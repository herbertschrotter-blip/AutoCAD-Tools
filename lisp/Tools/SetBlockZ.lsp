;;; ============================================================================
;;; SetBlockZ.lsp
;;; Setzt Block-Z-Koordinaten aus Attributwerten (Vermessungshöhen)
;;;
;;; Version: 1.24.0
;;; Datum: 2026-03-22
;;; Autor: Herbert Schrotter
;;; Namespace: SBZ (SetBlockZ)
;;;
;;; Beschreibung:
;;; Architekten liefern Pläne bei denen Vermessungsblöcke auf Z=0 stehen.
;;; Die tatsächliche Höhe steht als Attributwert im Block.
;;; Dieses Script setzt die Z-Koordinate aller Blockinstanzen auf den
;;; Attributwert (abzüglich Bau-0-Höhe), damit ein 3D-Geländemodell
;;; erstellt werden kann (z.B. für Leica).
;;;
;;; AppData: %APPDATA%\AutoCAD\Lisp\SetBlockZ\
;;;   - Log:    Log\SetBlockZ_YYYYMMDD_HHMMSS.log
;;;   - Config: Config\SetBlockZ.cfg
;;;
;;; Installation:
;;; 1. APPLOAD ausführen
;;; 2. SetBlockZ.lsp laden
;;; 3. Optional: Startup Suite für automatisches Laden
;;;
;;; Befehle:
;;; SETBLOCKZ    - Hauptbefehl: Blöcke nach Attribut auf Z setzen
;;; SBZSETTINGS  - Einstellungen (Bau-0, Toggles, Neuberechnung)
;;; SBZIMPORT    - Leica Vermessungspunkte importieren
;;; SBZPURGE     - Kopie-Blöcke löschen + Block-Definition purgen
;;; SBZDEBUG     - Debug-Modus ein/aus
;;; ============================================================================


;;; ============================================================================
;;; KONFIGURATION (KONSTANTEN)
;;; ============================================================================

(setq *SBZ:version* "1.24.0")
(setq *SBZ:namespace* "SBZ")
(setq *SBZ:appdata-folder* "SetBlockZ")

;; Custom Property Name fuer Bau-0-Hoehe in DWG SummaryInfo
(setq *SBZ:cp-bau0* "SetBlockZ_Bau0")
;; Custom Property fuer letzten Blockname und Attribut-Tag (pro DWG!)
(setq *SBZ:cp-blockname* "SetBlockZ_BlockName")
(setq *SBZ:cp-attrtag* "SetBlockZ_AttrTag")
(setq *SBZ:cp-scale* "SetBlockZ_Scale")
(setq *SBZ:cp-suffix* "SetBlockZ_Suffix")
(setq *SBZ:cp-font* "SetBlockZ_Font")


;;; ============================================================================
;;; GLOBALE VARIABLEN
;;; ============================================================================

(setq *SBZ:initialized* nil)
(setq *SBZ:log-session-id* nil)
(setq *SBZ:debug-mode* nil)

;; Config-Werte (Defaults) — nur Toggles, NICHT zeichnungsspezifisch
(setq *SBZ:cfg-byblock* 1)          ;; Farbe auf ByBlock setzen (0/1)
(setq *SBZ:cfg-movelayer* 0)        ;; Block auf Ziel-Layer verschieben (0/1)
(setq *SBZ:cfg-target-layer* "")    ;; Ziel-Layer Name
(setq *SBZ:cfg-copymode* 1)         ;; Kopie-Modus: Standard EIN (0/1)
(setq *SBZ:cfg-copyblock* "VM_Hoehe") ;; Blockname fuer Kopie-Block
(setq *SBZ:cfg-copylayer* "HP")     ;; Gegenstandsgruppe: HP=Hoehenpunkt, GP=Grenzpunkt, GE=Gelaende, FP=Festpunkt
(setq *SBZ:cfg-freeze-abs* 0)       ;; AttABS Layer einfrieren (0=sichtbar, 1=gefroren)
(setq *SBZ:cfg-freeze-rel* 0)       ;; AttREL Layer einfrieren (0=sichtbar, 1=gefroren)
(setq *SBZ:cfg-freeze-bau0* 1)      ;; AttBAU0 Layer einfrieren (0=sichtbar, 1=gefroren)
(setq *SBZ:cfg-font* "Arial")       ;; Schriftart fuer Attribute (TTF-Name)
;; Farben: ACI-Index (1=Rot,2=Gelb,3=Gruen,4=Cyan,5=Blau,6=Magenta,7=Weiss,256=VonLayer)
;; Attribut-Farbe 0 = Von Block (ByBlock)
(setq *SBZ:cfg-color-block* 7)      ;; Block-Symbol Farbe (ACI, Default: Weiss)
(setq *SBZ:cfg-color-abs* 0)        ;; HOEHE_ABS Attribut-Farbe (0=Von Block)
(setq *SBZ:cfg-color-rel* 0)        ;; HOEHE_REL Attribut-Farbe (0=Von Block)
(setq *SBZ:cfg-color-bau0* 0)       ;; HOEHE_BAU0 Attribut-Farbe (0=Von Block)


;;; ============================================================================
;;; APPDATA & LOGGING
;;; ============================================================================

;;; ----------------------------------------------------------------------------
;;; SBZ:get-appdata-path
;;; Gibt den AppData-Basisordner zurueck, erstellt Struktur falls noetig
;;; Rueckgabe: Pfad-String (ohne trailing Backslash)
;;; ----------------------------------------------------------------------------
(defun SBZ:get-appdata-path ( / base)
  (setq base (strcat (getenv "APPDATA") "\\AutoCAD\\Lisp\\" *SBZ:appdata-folder*))
  (if (not (vl-file-directory-p base))
    (progn
      (vl-mkdir (strcat (getenv "APPDATA") "\\AutoCAD"))
      (vl-mkdir (strcat (getenv "APPDATA") "\\AutoCAD\\Lisp"))
      (vl-mkdir base)
      (vl-mkdir (strcat base "\\Log"))
      (vl-mkdir (strcat base "\\Config"))
      (vl-mkdir (strcat base "\\Backup"))
    )
  )
  base
)


;;; ----------------------------------------------------------------------------
;;; SBZ:log-write
;;; Schreibt eine Zeile ins Session-Log
;;; Parameter:
;;;   level   - "INFO", "WARN", "ERROR", "DEBUG"
;;;   message - Beliebiger String
;;; ----------------------------------------------------------------------------
(defun SBZ:log-write (level message / appdata log-path fp timestamp)
  ;; DEBUG nur wenn aktiviert
  (if (and (= level "DEBUG") (not *SBZ:debug-mode*))
    nil ;; Skip
    (progn
      ;; Session-Log-Pfad beim ersten Schreiben erstellen
      (if (not *SBZ:log-session-id*)
        (progn
          (setq *SBZ:log-session-id*
            (strcat *SBZ:appdata-folder* "_"
              (menucmd "M=$(edtime,0,YYYYMMDD_HHMMSS)")
            )
          )
          ;; Log-Rotation beim ersten Schreiben
          (SBZ:log-rotate)
        )
      )
      (setq appdata (SBZ:get-appdata-path))
      (setq log-path (strcat appdata "\\Log\\" *SBZ:log-session-id* ".log"))
      ;; Timestamp
      (setq timestamp (menucmd "M=$(edtime,0,YYYY-MO-DD HH:MM:SS)"))
      ;; Schreiben
      (setq fp (open log-path "a"))
      (if fp
        (progn
          (write-line
            (strcat "[" timestamp "] ["
              (substr (strcat level "     ") 1 5)
              "] " message)
            fp)
          (close fp)
        )
      )
    )
  )
)


;;; ----------------------------------------------------------------------------
;;; SBZ:log-rotate
;;; Loescht alte Logs, behaelt nur die 5 neuesten
;;; ----------------------------------------------------------------------------
(defun SBZ:log-rotate ( / appdata log-dir files sorted-files delete-count i)
  (setq appdata (SBZ:get-appdata-path))
  (setq log-dir (strcat appdata "\\Log"))
  ;; Alle Log-Dateien finden
  (setq files (vl-directory-files log-dir (strcat *SBZ:appdata-folder* "_*.log") 1))
  (if files
    (progn
      ;; Sortieren (Dateiname enthaelt Timestamp = chronologisch)
      (setq sorted-files (vl-sort files '<))
      ;; Wenn mehr als 4 vorhanden (5. ist die aktuelle, noch nicht erstellt)
      (setq delete-count (- (length sorted-files) 4))
      (if (> delete-count 0)
        (progn
          (setq i 0)
          (repeat delete-count
            (vl-file-delete (strcat log-dir "\\" (nth i sorted-files)))
            (setq i (1+ i))
          )
        )
      )
    )
  )
)


;;; ============================================================================
;;; CONFIG-MANAGEMENT (AppData - fuer Toggles und Letzte-Wahl)
;;; ============================================================================

;;; ----------------------------------------------------------------------------
;;; SBZ:load-config
;;; Laedt Config aus AppData\Config\SetBlockZ.cfg
;;; Format: KEY=VALUE pro Zeile
;;; ----------------------------------------------------------------------------
(defun SBZ:load-config ( / appdata cfg-path fp line pos key val)
  (setq appdata (SBZ:get-appdata-path))
  (setq cfg-path (strcat appdata "\\Config\\" *SBZ:appdata-folder* ".cfg"))
  (if (findfile cfg-path)
    (progn
      (setq fp (open cfg-path "r"))
      (while (setq line (read-line fp))
        (setq pos (vl-string-search "=" line))
        (if pos
          (progn
            (setq key (substr line 1 pos))
            (setq val (substr line (+ pos 2)))
            (cond
              ((= key "BYBLOCK")    (setq *SBZ:cfg-byblock* (atoi val)))
              ((= key "MOVELAYER")  (setq *SBZ:cfg-movelayer* (atoi val)))
              ((= key "TARGETLAYER")(setq *SBZ:cfg-target-layer* val))
              ((= key "COPYMODE")   (setq *SBZ:cfg-copymode* (atoi val)))
              ((= key "COPYBLOCK")  (setq *SBZ:cfg-copyblock* val))
              ((= key "COPYLAYER")  (setq *SBZ:cfg-copylayer* val))
              ((= key "FREEZEABS") (setq *SBZ:cfg-freeze-abs* (atoi val)))
              ((= key "FREEZEREL") (setq *SBZ:cfg-freeze-rel* (atoi val)))
              ((= key "FREEZEBAU0")(setq *SBZ:cfg-freeze-bau0* (atoi val)))
              ((= key "FONT")      (setq *SBZ:cfg-font* val))
              ((= key "COLORBLOCK")(setq *SBZ:cfg-color-block* (atoi val)))
              ((= key "COLORABS")  (setq *SBZ:cfg-color-abs* (atoi val)))
              ((= key "COLORREL")  (setq *SBZ:cfg-color-rel* (atoi val)))
              ((= key "COLORBAU0") (setq *SBZ:cfg-color-bau0* (atoi val)))
            )
          )
        )
      )
      (close fp)
      (SBZ:log-write "INFO" (strcat "Config geladen: " cfg-path))
    )
    ;; Keine Config → Defaults bleiben
    (SBZ:log-write "WARN" "Keine Config gefunden, verwende Defaults")
  )
)


;;; ----------------------------------------------------------------------------
;;; SBZ:save-config
;;; Speichert Config in AppData\Config\SetBlockZ.cfg
;;; ----------------------------------------------------------------------------
(defun SBZ:save-config ( / appdata cfg-path fp)
  (setq appdata (SBZ:get-appdata-path))
  (setq cfg-path (strcat appdata "\\Config\\" *SBZ:appdata-folder* ".cfg"))
  (setq fp (open cfg-path "w"))
  (if fp
    (progn
      (write-line (strcat "VERSION=" *SBZ:version*) fp)
      (write-line (strcat "BYBLOCK=" (itoa *SBZ:cfg-byblock*)) fp)
      (write-line (strcat "MOVELAYER=" (itoa *SBZ:cfg-movelayer*)) fp)
      (write-line (strcat "TARGETLAYER=" *SBZ:cfg-target-layer*) fp)
      (write-line (strcat "COPYMODE=" (itoa *SBZ:cfg-copymode*)) fp)
      (write-line (strcat "COPYBLOCK=" *SBZ:cfg-copyblock*) fp)
      (write-line (strcat "COPYLAYER=" *SBZ:cfg-copylayer*) fp)
      (write-line (strcat "FREEZEABS=" (itoa *SBZ:cfg-freeze-abs*)) fp)
      (write-line (strcat "FREEZEREL=" (itoa *SBZ:cfg-freeze-rel*)) fp)
      (write-line (strcat "FREEZEBAU0=" (itoa *SBZ:cfg-freeze-bau0*)) fp)
      (write-line (strcat "FONT=" *SBZ:cfg-font*) fp)
      (write-line (strcat "COLORBLOCK=" (itoa *SBZ:cfg-color-block*)) fp)
      (write-line (strcat "COLORABS=" (itoa *SBZ:cfg-color-abs*)) fp)
      (write-line (strcat "COLORREL=" (itoa *SBZ:cfg-color-rel*)) fp)
      (write-line (strcat "COLORBAU0=" (itoa *SBZ:cfg-color-bau0*)) fp)
      (close fp)
      (SBZ:log-write "INFO" (strcat "Config gespeichert: " cfg-path))
    )
    (SBZ:log-write "ERROR" (strcat "Config konnte nicht geschrieben werden: " cfg-path))
  )
)


;;; ============================================================================
;;; CUSTOM PROPERTIES (in DWG SummaryInfo - wandern mit der Zeichnung!)
;;; ============================================================================
;;; Gespeichert werden:
;;;   SetBlockZ_Bau0      — Bau-0-Hoehe (String, z.B. "322.450")
;;;   SetBlockZ_BlockName  — Zuletzt verarbeiteter Blockname
;;;   SetBlockZ_AttrTag    — Zuletzt gewaehltes Attribut-Tag

;;; ----------------------------------------------------------------------------
;;; SBZ:get-custom-prop
;;; Generisch: Liest eine Custom Property aus DWG SummaryInfo
;;; Parameter: prop-name - Name der Property (String)
;;; Rueckgabe: Wert als String oder nil wenn nicht vorhanden
;;; ----------------------------------------------------------------------------
(defun SBZ:get-custom-prop (prop-name / doc si num-props i key val result)
  (setq doc (vla-get-activedocument (vlax-get-acad-object)))
  (setq si (vla-get-summaryinfo doc))
  (setq num-props (vla-numcustominfo si))
  (setq result nil)
  (setq i 0)
  (while (and (not result) (< i num-props))
    (vla-getcustombyindex si i 'key 'val)
    (setq key (SBZ:safe-variant-value key))
    (setq val (SBZ:safe-variant-value val))
    (if (= (strcase key) (strcase prop-name))
      (setq result val)
    )
    (setq i (1+ i))
  )
  result
)


;;; ----------------------------------------------------------------------------
;;; SBZ:set-custom-prop
;;; Generisch: Schreibt/aktualisiert eine Custom Property in DWG SummaryInfo
;;; Parameter:
;;;   prop-name  - Name der Property (String)
;;;   prop-value - Wert als String
;;; Rueckgabe: T bei Erfolg
;;; ----------------------------------------------------------------------------
(defun SBZ:set-custom-prop (prop-name prop-value / doc si num-props i key val found)
  (setq doc (vla-get-activedocument (vlax-get-acad-object)))
  (setq si (vla-get-summaryinfo doc))
  (setq num-props (vla-numcustominfo si))
  (setq found nil)
  ;; Pruefen ob Property schon existiert → Update
  (setq i 0)
  (while (and (not found) (< i num-props))
    (vla-getcustombyindex si i 'key 'val)
    (setq key (SBZ:safe-variant-value key))
    (if (= (strcase key) (strcase prop-name))
      (progn
        (vla-setcustombyindex si i prop-name prop-value)
        (setq found T)
      )
    )
    (setq i (1+ i))
  )
  ;; Nicht vorhanden → neu anlegen
  (if (not found)
    (progn
      (vla-addcustominfo si prop-name prop-value)
      (setq found T)
    )
  )
  (SBZ:log-write "DEBUG" (strcat "Custom Property '" prop-name "' = '" prop-value "'"))
  found
)


;;; --- Convenience-Wrapper fuer die 3 Properties ---

;;; Bau-0-Hoehe lesen (Real oder nil)
(defun SBZ:get-bau0 ( / val)
  (setq val (SBZ:get-custom-prop *SBZ:cp-bau0*))
  (if val
    (atof (vl-string-subst "." "," val))
    nil
  )
)

;;; Bau-0-Hoehe schreiben
(defun SBZ:set-bau0 (hoehe)
  (SBZ:set-custom-prop *SBZ:cp-bau0* (rtos hoehe 2 3))
  (SBZ:log-write "INFO" (strcat "Bau-0 gespeichert: " (rtos hoehe 2 3)))
)

;;; Letzter Blockname lesen (String oder nil)
(defun SBZ:get-last-blockname ()
  (SBZ:get-custom-prop *SBZ:cp-blockname*)
)

;;; Letzter Blockname schreiben
(defun SBZ:set-last-blockname (name)
  (SBZ:set-custom-prop *SBZ:cp-blockname* name)
)

;;; Letztes Attribut-Tag lesen (String oder nil)
(defun SBZ:get-last-attrtag ()
  (SBZ:get-custom-prop *SBZ:cp-attrtag*)
)

;;; Letztes Attribut-Tag schreiben
(defun SBZ:set-last-attrtag (tag)
  (SBZ:set-custom-prop *SBZ:cp-attrtag* tag)
)

;;; Block-Skalierung lesen (Real, Default 1.0)
(defun SBZ:get-scale ( / val)
  (setq val (SBZ:get-custom-prop *SBZ:cp-scale*))
  (if (and val (/= val ""))
    (atof val)
    1.0
  )
)

;;; Block-Skalierung schreiben
(defun SBZ:set-scale (scale)
  (SBZ:set-custom-prop *SBZ:cp-scale* (rtos scale 2 4))
  (SBZ:log-write "INFO" (strcat "Skalierung gespeichert: " (rtos scale 2 4)))
)

;;; Suffix lesen (String, Default "m ü. A.")
(defun SBZ:get-suffix ( / val)
  (setq val (SBZ:get-custom-prop *SBZ:cp-suffix*))
  (if (and val (/= val ""))
    val
    "m ü. A."
  )
)

;;; Suffix schreiben
(defun SBZ:set-suffix (s)
  (SBZ:set-custom-prop *SBZ:cp-suffix* s)
  (SBZ:log-write "INFO" (strcat "Suffix gespeichert: '" s "'"))
)

;;; Schriftart lesen (String, Default "Arial")
(defun SBZ:get-font ( / val)
  (setq val (SBZ:get-custom-prop *SBZ:cp-font*))
  (if (and val (/= val ""))
    val
    *SBZ:cfg-font*
  )
)

;;; Schriftart schreiben
(defun SBZ:set-font (f)
  (SBZ:set-custom-prop *SBZ:cp-font* f)
  (SBZ:log-write "INFO" (strcat "Schriftart gespeichert: '" f "'"))
)


;;; ============================================================================
;;; HILFSFUNKTIONEN
;;; ============================================================================

;;; ----------------------------------------------------------------------------
;;; SBZ:rtos-fixed
;;; rtos mit erzwungenen Nachkommastellen (DIMZIN wird temporaer auf 0 gesetzt)
;;; AutoCADs rtos unterdrueckt trailing Zeros wenn DIMZIN Bit 8 gesetzt ist.
;;; Parameter:
;;;   val  - Zahl (Real)
;;;   prec - Anzahl Nachkommastellen (Integer)
;;; Rueckgabe: String mit exakt prec Nachkommastellen
;;; ----------------------------------------------------------------------------
(defun SBZ:rtos-fixed (val prec / old-dimzin result)
  (setq old-dimzin (getvar "DIMZIN"))
  (setvar "DIMZIN" 0)
  (setq result (rtos val 2 prec))
  (setvar "DIMZIN" old-dimzin)
  result
)


;;; ----------------------------------------------------------------------------
;;; SBZ:safe-variant-value
;;; Sicheres Auslesen: String oder Variant
;;; GetCustomByIndex gibt manchmal Strings direkt, manchmal Variants zurueck
;;; Parameter: val - String oder Variant
;;; Rueckgabe: String
;;; ----------------------------------------------------------------------------
(defun SBZ:safe-variant-value (val / )
  (cond
    ((= (type val) 'STR) val)
    ((= (type val) 'VLA-OBJECT) (vlax-variant-value val))
    ((not (null val))
      (vl-catch-all-apply 'vlax-variant-value (list val))
    )
    (T "")
  )
)


;;; ----------------------------------------------------------------------------
;;; SBZ:cancel-p
;;; Prueft ob User abgebrochen hat (ESC, Cancel, etc.)
;;; Funktioniert in deutscher UND englischer AutoCAD-Version
;;; Parameter: msg - Fehlermeldung-String
;;; Rueckgabe: T wenn Cancel, nil sonst
;;; ----------------------------------------------------------------------------
(defun SBZ:cancel-p (msg)
  (wcmatch (strcase msg)
    "*ABBRUCH*,*ABGEBROCHEN*,*CANCEL*,*QUIT*,*EXIT*"
  )
)


;;; ============================================================================
;;; GRUPPEN-VERWALTUNG (XRecord + XData in DWG)
;;; ============================================================================
;;; Jeder SETBLOCKZ-Durchlauf erstellt eine "Gruppe" mit eigenem Namen.
;;; Die Gruppen-Settings werden als XRecord im Named Object Dictionary
;;; gespeichert. Jede Kopie-Block-Instanz bekommt XData mit dem Gruppennamen.
;;;
;;; NOD → SBZ_Groups (Dictionary)
;;;         ├── "STAB137" (XRecord) → Settings als DXF 1000-Strings
;;;         └── "GRENZ"   (XRecord) → ...
;;;
;;; CopyBlock-Name = <BasisName>_<Gruppenname> (z.B. "VM_Hoehe_STAB137")
;;; Jede Gruppe hat eigene Block-Definition → verschiedene Fonts/Farben moeglich.
;;;
;;; XData auf jeder Kopie-Block-Instanz:
;;;   App "SBZ", DXF 1000 = Gruppenname
;;; ============================================================================

;;; --- XData App registrieren ---
(defun SBZ:regapp ( / )
  (if (not (tblsearch "APPID" "SBZ"))
    (regapp "SBZ")
  )
)


;;; ----------------------------------------------------------------------------
;;; SBZ:set-xdata
;;; Schreibt XData mit Gruppenname + Quell-Handle auf eine Entity
;;; Parameter:
;;;   ent          - Entity-Name (ename) des Kopie-Blocks
;;;   group-name   - Gruppenname (String)
;;;   source-handle - Handle des Quell-Blocks (String, oder nil)
;;; ----------------------------------------------------------------------------
(defun SBZ:set-xdata (ent group-name source-handle / ent-data xdata-list)
  (SBZ:regapp)
  (setq ent-data (entget ent '("SBZ")))
  ;; Alte XData entfernen falls vorhanden
  (if (assoc -3 ent-data)
    (setq ent-data (vl-remove (assoc -3 ent-data) ent-data))
  )
  ;; Neue XData: DXF 1000 = Gruppenname, DXF 1005 = Quell-Handle
  ;; DXF 1005 ist speziell fuer Handles — AutoCAD aktualisiert bei WBLOCK/INSERT!
  (if (and source-handle (/= source-handle ""))
    (setq xdata-list
      (list -3 (list "SBZ"
        (cons 1000 group-name)
        (cons 1005 source-handle))))
    (setq xdata-list
      (list -3 (list "SBZ"
        (cons 1000 group-name))))
  )
  (setq ent-data (append ent-data (list xdata-list)))
  (entmod ent-data)
)


;;; ----------------------------------------------------------------------------
;;; SBZ:get-xdata
;;; Liest den Gruppennamen aus XData einer Entity
;;; Parameter: ent - Entity-Name (ename)
;;; Rueckgabe: Gruppenname (String) oder nil
;;; ----------------------------------------------------------------------------
(defun SBZ:get-xdata (ent / ent-data xdata app-data)
  (setq ent-data (entget ent '("SBZ")))
  (setq xdata (assoc -3 ent-data))
  (if xdata
    (progn
      (setq app-data (cdr (assoc "SBZ" (cdr xdata))))
      (if app-data
        (cdr (assoc 1000 app-data))
        nil
      )
    )
    nil
  )
)


;;; ----------------------------------------------------------------------------
;;; SBZ:get-xdata-handle
;;; Liest das Quell-Block Handle aus XData einer Kopie-Block Entity
;;; Parameter: ent - Entity-Name (ename)
;;; Rueckgabe: Handle-String (z.B. "2A3F") oder nil
;;; ----------------------------------------------------------------------------
(defun SBZ:get-xdata-handle (ent / ent-data xdata app-data)
  (setq ent-data (entget ent '("SBZ")))
  (setq xdata (assoc -3 ent-data))
  (if xdata
    (progn
      (setq app-data (cdr (assoc "SBZ" (cdr xdata))))
      (if app-data
        (cdr (assoc 1005 app-data))
        nil
      )
    )
    nil
  )
)


;;; ----------------------------------------------------------------------------
;;; SBZ:get-group-entities
;;; Findet alle INSERT-Entities die zur angegebenen Gruppe gehoeren
;;; Parameter: group-name - Gruppenname (String)
;;; Rueckgabe: Liste von enames oder nil
;;; ----------------------------------------------------------------------------
(defun SBZ:get-group-entities (group-name / ss i ent gname result)
  (setq result nil)
  ;; Alle INSERTs mit SBZ XData im Modelspace suchen
  (setq ss (ssget "X" (list '(0 . "INSERT") '(410 . "Model") '(-3 ("SBZ")))))
  (if (and ss (> (sslength ss) 0))
    (progn
      (setq i (sslength ss))
      (while (> (setq i (1- i)) -1)
        (setq ent (ssname ss i))
        (setq gname (SBZ:get-xdata ent))
        (if (and gname (= (strcase gname) (strcase group-name)))
          (setq result (cons ent result))
        )
      )
    )
  )
  result
)


;;; Sauberer Ansatz fuer Named Object Dictionary via entget/entmake:

;;; ----------------------------------------------------------------------------
;;; SBZ:nod-get-dict
;;; Holt oder erstellt das SBZ_Groups Dictionary im Named Object Dictionary
;;; Verwendet entget-basiertes NOD (zuverlaessiger als VLA fuer Dicts)
;;; Rueckgabe: Entity-Name des Dictionary (ename) oder nil
;;; ----------------------------------------------------------------------------
(defun SBZ:nod-get-dict ( / nod-ent nod-data dict-name result)
  (setq dict-name "SBZ_Groups")
  ;; Named Object Dictionary = Entity (namedobjdict)
  (setq nod-ent (namedobjdict))
  (setq result (dictsearch nod-ent dict-name))
  (if result
    ;; Dictionary existiert → Entity-Name zurueckgeben
    (cdr (assoc -1 result))
    ;; Nicht vorhanden → neues Dictionary erstellen
    (progn
      (setq result
        (entmakex '((0 . "DICTIONARY") (100 . "AcDbDictionary"))))
      (if result
        (progn
          (dictadd nod-ent dict-name result)
          (SBZ:log-write "INFO" "SBZ_Groups Dictionary erstellt")
          result
        )
        (progn
          (SBZ:log-write "ERROR" "SBZ_Groups Dictionary konnte nicht erstellt werden")
          nil
        )
      )
    )
  )
)


;;; ----------------------------------------------------------------------------
;;; SBZ:save-group
;;; Speichert Gruppen-Settings als XRecord im SBZ_Groups Dictionary
;;; Parameter:
;;;   group-name  - Gruppenname (String)
;;;   group-data  - Assoziationsliste mit Settings:
;;;     ("QUELLBLOCK" . "STAB137")
;;;     ("ATTRTAG"    . "Punkthoehe")
;;;     ("BAU0"       . "320.390")     ;; "" = DWG-Standard verwenden
;;;     ("ZMODE"      . "REL")
;;;     ("COPYBLOCK"  . "VM_Hoehe_STAB137")
;;;     ("COPYLAYER"  . "HP")
;;;     ("SCALE"      . "10.0000")
;;;     ("SUFFIX"     . "m ue. A.")
;;;     ("FONT"       . "Arial")
;;;     ("COLORBLOCK" . "7")
;;;     ("COLORABS"   . "0")
;;;     ("COLORREL"   . "0")
;;;     ("COLORBAU0"  . "0")
;;;     ("FREEZEABS"  . "0")
;;;     ("FREEZEREL"  . "0")
;;;     ("FREEZEBAU0" . "1")
;;; Rueckgabe: T bei Erfolg
;;; ----------------------------------------------------------------------------
(defun SBZ:save-group (group-name group-data / dict-ent old-rec xrec dxf-list)
  (setq dict-ent (SBZ:nod-get-dict))
  (if (not dict-ent)
    (progn
      (SBZ:log-write "ERROR" "Kann SBZ_Groups Dictionary nicht oeffnen")
      nil
    )
    (progn
      ;; Altes XRecord loeschen falls vorhanden
      (setq old-rec (dictsearch dict-ent group-name))
      (if old-rec
        (progn
          ;; Erst aus Dictionary entfernen, DANN Entity loeschen
          (dictremove dict-ent group-name)
          (entdel (cdr (assoc -1 old-rec)))
          (SBZ:log-write "DEBUG"
            (strcat "Altes XRecord fuer '" group-name "' entfernt"))
        )
      )
      ;; DXF-Liste aufbauen: XRecord mit DXF 1000 (String) pro Setting
      ;; Format: "KEY=VALUE" pro DXF 1000 Eintrag
      (setq dxf-list
        (list '(0 . "XRECORD")
              '(100 . "AcDbXrecord")
        )
      )
      (foreach pair group-data
        (setq dxf-list
          (append dxf-list
            (list (cons 1 (strcat (car pair) "=" (cdr pair))))
          )
        )
      )
      ;; XRecord erstellen
      (setq xrec (entmakex dxf-list))
      (if xrec
        (progn
          (dictadd dict-ent group-name xrec)
          (SBZ:log-write "INFO"
            (strcat "Gruppe '" group-name "' gespeichert ("
                    (itoa (length group-data)) " Settings)"))
          T
        )
        (progn
          (SBZ:log-write "ERROR"
            (strcat "XRecord fuer Gruppe '" group-name "' konnte nicht erstellt werden"))
          nil
        )
      )
    )
  )
)


;;; ----------------------------------------------------------------------------
;;; SBZ:load-group
;;; Laedt Gruppen-Settings aus XRecord
;;; Parameter: group-name - Gruppenname (String)
;;; Rueckgabe: Assoziationsliste (("KEY" . "VALUE") ...) oder nil
;;; ----------------------------------------------------------------------------
(defun SBZ:load-group (group-name / dict-ent rec-data result pair pos key val)
  (setq dict-ent (SBZ:nod-get-dict))
  (if (not dict-ent)
    nil
    (progn
      (setq rec-data (dictsearch dict-ent group-name))
      (if (not rec-data)
        nil
        (progn
          (setq result nil)
          ;; Alle DXF 1 Eintraege lesen (KEY=VALUE Format)
          (foreach item rec-data
            (if (= (car item) 1)
              (progn
                (setq pair (cdr item))
                (setq pos (vl-string-search "=" pair))
                (if pos
                  (progn
                    (setq key (substr pair 1 pos))
                    (setq val (substr pair (+ pos 2)))
                    (setq result (cons (cons key val) result))
                  )
                )
              )
            )
          )
          ;; Liste umdrehen (war durch cons umgekehrt)
          (reverse result)
        )
      )
    )
  )
)


;;; ----------------------------------------------------------------------------
;;; SBZ:get-group-names
;;; Gibt alle Gruppennamen zurueck
;;; Rueckgabe: Liste von Strings oder nil
;;; ----------------------------------------------------------------------------
(defun SBZ:get-group-names ( / dict-ent dict-data result ent rec-data)
  (setq dict-ent (SBZ:nod-get-dict))
  (if (not dict-ent)
    nil
    (progn
      (setq result nil)
      (setq dict-data (entget dict-ent))
      ;; DXF 3 = Dictionary-Eintragsname, DXF 350 = Handle
      (foreach item dict-data
        (if (= (car item) 3)
          (setq result (cons (cdr item) result))
        )
      )
      (reverse result)
    )
  )
)


;;; ----------------------------------------------------------------------------
;;; SBZ:cleanup-group-layers
;;; Loescht die Layer einer Gruppe wenn sie leer sind (keine Entities darauf)
;;; Loescht: Basis-Layer + _abs/_rel Varianten + Attribut-Sub-Layer
;;; Parameter: group-data - Assoziationsliste der Gruppe
;;; ----------------------------------------------------------------------------
(defun SBZ:cleanup-group-layers (group-data / base-layer group-name vlay layer-names
                                              doc layers lay-obj lay-name)
  (setq base-layer (cdr (assoc "COPYLAYER" group-data)))
  ;; Gruppenname aus COPYBLOCK ableiten (letzter Teil nach letztem _)
  ;; Oder direkt aus group-data lesen wenn vorhanden
  (setq group-name (cdr (assoc "GROUPNAME" group-data)))
  (if (not base-layer) (setq base-layer ""))
  (if (= base-layer "") nil
    (progn
      ;; VM_<Gruppe>_<Gruppenname> + Attribut-Sub-Layer (aktuell)
      (setq vlay
        (if (and group-name (/= group-name ""))
          (strcat "VM_" base-layer "_" group-name)
          (strcat "VM_" base-layer)
        )
      )
      (setq layer-names
        (list
          vlay
          (strcat vlay "-AttABS")
          (strcat vlay "-AttREL")
          (strcat vlay "-AttBAU0")
          ;; Alte V_ Layer-Formate aufraeumen (vor v1.20.0)
          (if (and group-name (/= group-name ""))
            (strcat "V_" base-layer "_" group-name)
            (strcat "V_" base-layer))
          (if (and group-name (/= group-name ""))
            (strcat "V_" base-layer "_" group-name "-AttABS") "")
          (if (and group-name (/= group-name ""))
            (strcat "V_" base-layer "_" group-name "-AttREL") "")
          (if (and group-name (/= group-name ""))
            (strcat "V_" base-layer "_" group-name "-AttBAU0") "")
          ;; Noch aeltere Formate (vor v1.19.1)
          base-layer
          (strcat base-layer "_abs")
          (strcat base-layer "_rel")
          (strcat base-layer "_abs-AttABS")
          (strcat base-layer "_abs-AttREL")
          (strcat base-layer "_abs-AttBAU0")
          (strcat base-layer "_rel-AttABS")
          (strcat base-layer "_rel-AttREL")
          (strcat base-layer "_rel-AttBAU0")
        )
      )
      (setq doc (vla-get-activedocument (vlax-get-acad-object)))
      (setq layers (vla-get-layers doc))
      (foreach lay-name layer-names
        (if (not (vl-catch-all-error-p
              (setq lay-obj (vl-catch-all-apply 'vla-item (list layers lay-name)))))
          (progn
            (if (not (ssget "X" (list (cons 8 lay-name))))
              (if (not (vl-catch-all-error-p
                    (vl-catch-all-apply 'vla-delete (list lay-obj))))
                (SBZ:log-write "INFO"
                  (strcat "Leerer Layer '" lay-name "' geloescht"))
                (SBZ:log-write "DEBUG"
                  (strcat "Layer '" lay-name "' konnte nicht geloescht werden"))
              )
            )
          )
        )
      )
    )
  )
)


;;; ----------------------------------------------------------------------------
;;; SBZ:delete-group
;;; Loescht eine Gruppe: XRecord + alle zugehoerigen Block-Instanzen + Definition
;;; Parameter: group-name - Gruppenname (String)
;;; Rueckgabe: Anzahl geloeschter Instanzen
;;; ----------------------------------------------------------------------------
(defun SBZ:delete-group (group-name / dict-ent old-rec group-data
                                      copy-blk-name ents count blocks blk-def)
  ;; 1. Gruppen-Settings laden um CopyBlock-Namen zu erfahren
  (setq group-data (SBZ:load-group group-name))
  (setq copy-blk-name
    (if group-data
      (cdr (assoc "COPYBLOCK" group-data))
      nil
    )
  )
  ;; 2. Alle Instanzen dieser Gruppe loeschen (via XData)
  (setq ents (SBZ:get-group-entities group-name))
  (setq count (length ents))
  (if (> count 0)
    (progn
      (foreach ent ents (entdel ent))
      (SBZ:log-write "INFO"
        (strcat (itoa count) " Instanzen der Gruppe '" group-name "' geloescht"))
    )
  )
  ;; 3. Block-Definition loeschen
  (if copy-blk-name
    (progn
      (setq blocks (vla-get-blocks
        (vla-get-activedocument (vlax-get-acad-object))))
      (if (not (vl-catch-all-error-p
            (setq blk-def (vl-catch-all-apply 'vla-item
              (list blocks copy-blk-name)))))
        (progn
          (vl-catch-all-apply 'vla-delete (list blk-def))
          (SBZ:log-write "INFO"
            (strcat "Block-Definition '" copy-blk-name "' geloescht"))
        )
      )
    )
  )
  ;; 4. Gruppen-Layer aufraeumen
  (if group-data
    (SBZ:cleanup-group-layers group-data)
  )
  ;; 5. XRecord aus Dictionary loeschen
  (setq dict-ent (SBZ:nod-get-dict))
  (if dict-ent
    (progn
      (setq old-rec (dictsearch dict-ent group-name))
      (if old-rec
        (progn
          (dictremove dict-ent group-name)
          (entdel (cdr (assoc -1 old-rec)))
          (SBZ:log-write "INFO"
            (strcat "Gruppe '" group-name "' aus Dictionary geloescht"))
        )
      )
    )
  )
  count
)


;;; ----------------------------------------------------------------------------
;;; SBZ:get-source-ss-for-group
;;; Findet die Quell-Bloecke die zu einer Gruppe gehoeren.
;;; Methode: Liest Quell-Handle (DXF 1005) aus XData der Kopie-Bloecke,
;;; dann findet die Quell-Bloecke via handent.
;;; Ein Quell-Block kann in mehreren Gruppen sein!
;;; Parameter:
;;;   group-name  - Gruppenname (String)
;;;   quell-block - Name des Quell-Blocks (String, nur fuer Logging)
;;; Rueckgabe: Selection Set der Quell-Bloecke oder nil
;;; ----------------------------------------------------------------------------
(defun SBZ:get-source-ss-for-group (group-name quell-block /
                                     group-ents ent src-handle src-ent
                                     ss-result handles-found)
  ;; 1. Alle Kopie-Bloecke der Gruppe finden (via XData Gruppenname)
  (setq group-ents (SBZ:get-group-entities group-name))
  (if (not group-ents)
    (progn
      (SBZ:log-write "WARN"
        (strcat "Keine Kopie-Bloecke fuer Gruppe '" group-name "' gefunden"))
      nil
    )
    (progn
      ;; 2. Quell-Handles aus XData lesen und Quell-Entities sammeln
      (setq ss-result (ssadd))
      (setq handles-found 0)
      (foreach ent group-ents
        (setq src-handle (SBZ:get-xdata-handle ent))
        (if src-handle
          (progn
            ;; Handle → Entity (handent gibt ename zurueck)
            (setq src-ent (handent src-handle))
            (if src-ent
              (progn
                (ssadd src-ent ss-result)
                (setq handles-found (1+ handles-found))
              )
              (SBZ:log-write "WARN"
                (strcat "Handle '" src-handle "' nicht gefunden (Quell-Block geloescht?)"))
            )
          )
          ;; Kein Handle → Fallback auf Position (fuer alte Gruppen ohne Handle)
          (SBZ:log-write "DEBUG"
            (strcat "Kopie-Block ohne Quell-Handle (alte Gruppe?)"))
        )
      )
      (SBZ:log-write "INFO"
        (strcat "Quell-Bloecke via Handle: " (itoa handles-found)
                " von " (itoa (length group-ents)) " Kopie-Bloecken"))
      (if (> (sslength ss-result) 0)
        ss-result
        nil
      )
    )
  )
)


;;; ----------------------------------------------------------------------------
;;; SBZ:build-copyblock-name
;;; Baut den CopyBlock-Namen aus Basis + Gruppenname
;;; Format: <BasisName>_<Gruppenname>
;;; Parameter:
;;;   group-name - Gruppenname (String)
;;; Rueckgabe: CopyBlock-Name (z.B. "VM_Hoehe_STAB137")
;;; ----------------------------------------------------------------------------
(defun SBZ:build-copyblock-name (group-name / )
  (strcat *SBZ:cfg-copyblock* "_" group-name)
)


;;; ----------------------------------------------------------------------------
;;; SBZ:group-data-from-current
;;; Erstellt eine Gruppen-Settings-Liste aus den aktuellen globalen Variablen
;;; Parameter:
;;;   quell-block - Quell-Blockname (String)
;;;   attr-tag    - Attribut-Tag (String)
;;;   bau0-str    - Bau-0 als String ("" = DWG-Standard verwenden)
;;;   z-mode      - "ABS" oder "REL"
;;;   group-name  - Gruppenname (fuer CopyBlock-Name)
;;; Rueckgabe: Assoziationsliste
;;; ----------------------------------------------------------------------------
(defun SBZ:group-data-from-current (quell-block attr-tag bau0-str z-mode group-name / )
  (list
    (cons "GROUPNAME"  group-name)
    (cons "QUELLBLOCK" quell-block)
    (cons "ATTRTAG"    attr-tag)
    (cons "BAU0"       bau0-str)
    (cons "ZMODE"      z-mode)
    (cons "COPYBLOCK"  (SBZ:build-copyblock-name group-name))
    (cons "COPYLAYER"  *SBZ:cfg-copylayer*)
    (cons "SCALE"      (rtos (SBZ:get-scale) 2 4))
    (cons "SUFFIX"     (SBZ:get-suffix))
    (cons "FONT"       (SBZ:get-font))
    (cons "COLORBLOCK" (itoa *SBZ:cfg-color-block*))
    (cons "COLORABS"   (itoa *SBZ:cfg-color-abs*))
    (cons "COLORREL"   (itoa *SBZ:cfg-color-rel*))
    (cons "COLORBAU0"  (itoa *SBZ:cfg-color-bau0*))
    (cons "FREEZEABS"  (itoa *SBZ:cfg-freeze-abs*))
    (cons "FREEZEREL"  (itoa *SBZ:cfg-freeze-rel*))
    (cons "FREEZEBAU0" (itoa *SBZ:cfg-freeze-bau0*))
  )
)


;;; ----------------------------------------------------------------------------
;;; SBZ:apply-group-settings
;;; Laedt Gruppen-Settings und setzt die globalen Variablen entsprechend
;;; Parameter: group-name - Gruppenname (String)
;;; Rueckgabe: T wenn geladen, nil wenn Gruppe nicht existiert
;;; ----------------------------------------------------------------------------
(defun SBZ:apply-group-settings (group-name / gdata val)
  (setq gdata (SBZ:load-group group-name))
  (if (not gdata)
    nil
    (progn
      ;; Globale Variablen aus Gruppen-Daten setzen
      (if (setq val (cdr (assoc "COPYLAYER" gdata)))
        (setq *SBZ:cfg-copylayer* val))
      (if (setq val (cdr (assoc "FONT" gdata)))
        (setq *SBZ:cfg-font* val))
      (if (setq val (cdr (assoc "COLORBLOCK" gdata)))
        (setq *SBZ:cfg-color-block* (atoi val)))
      (if (setq val (cdr (assoc "COLORABS" gdata)))
        (setq *SBZ:cfg-color-abs* (atoi val)))
      (if (setq val (cdr (assoc "COLORREL" gdata)))
        (setq *SBZ:cfg-color-rel* (atoi val)))
      (if (setq val (cdr (assoc "COLORBAU0" gdata)))
        (setq *SBZ:cfg-color-bau0* (atoi val)))
      (if (setq val (cdr (assoc "FREEZEABS" gdata)))
        (setq *SBZ:cfg-freeze-abs* (atoi val)))
      (if (setq val (cdr (assoc "FREEZEREL" gdata)))
        (setq *SBZ:cfg-freeze-rel* (atoi val)))
      (if (setq val (cdr (assoc "FREEZEBAU0" gdata)))
        (setq *SBZ:cfg-freeze-bau0* (atoi val)))
      ;; DWG Custom Properties setzen
      (if (setq val (cdr (assoc "SCALE" gdata)))
        (SBZ:set-scale (atof val)))
      (if (setq val (cdr (assoc "SUFFIX" gdata)))
        (SBZ:set-suffix val))
      (if (setq val (cdr (assoc "FONT" gdata)))
        (SBZ:set-font val))
      (SBZ:log-write "INFO"
        (strcat "Gruppen-Settings '" group-name "' geladen"))
      T
    )
  )
)


;;; ============================================================================
;;; LAZY-INIT
;;; ============================================================================

;;; ----------------------------------------------------------------------------
;;; SBZ:ensure-init
;;; Initialisierung beim ersten Befehlsaufruf
;;; Laedt VLA, Config, schreibt Start-Log
;;; ----------------------------------------------------------------------------
(defun SBZ:ensure-init ( / )
  (if (not *SBZ:initialized*)
    (progn
      ;; VLA laden
      (vl-load-com)
      ;; XData App registrieren
      (SBZ:regapp)
      ;; AppData-Ordner sicherstellen
      (SBZ:get-appdata-path)
      ;; Start-Log
      (SBZ:log-write "INFO"
        (strcat "=== SetBlockZ v" *SBZ:version* " gestartet ==="))
      ;; Config laden
      (SBZ:load-config)
      ;; Fertig
      (setq *SBZ:initialized* T)
      (SBZ:log-write "INFO" "Initialisierung abgeschlossen")
    )
  )
)


;;; ============================================================================
;;; DCL: FILTER-LISTBOX (Lee Mac Pattern, Embedded DCL)
;;; ============================================================================

;;; ----------------------------------------------------------------------------
;;; SBZ:filtlistbox
;;; Filterbarer Auswahldialog (Lee Mac Pattern)
;;; Parameter:
;;;   msg - Dialog-Titel
;;;   lst - Liste der Eintraege (Strings)
;;;   mtp - T fuer Multi-Select, nil fuer Single-Select
;;; Rueckgabe: Liste der gewaehlten Strings oder nil bei Abbruch
;;; ----------------------------------------------------------------------------
(defun SBZ:filtlistbox (msg lst mtp / dch des tmp rtn)
  (cond
    ((not
      (and
        (setq tmp (vl-filename-mktemp nil nil ".dcl"))
        (setq des (open tmp "w"))
        (write-line
          (strcat
            "sbz_listbox : dialog { label = \"" msg "\";"
            " spacer;"
            " : edit_box { key = \"filter\"; label = \"Filter:\"; value = \"*\"; }"
            " spacer;"
            " : list_box { key = \"list\"; multiple_select = "
            (if mtp "true" "false")
            "; width = 50; height = 15; }"
            " spacer; ok_cancel; }"
          )
          des
        )
        (not (close des))
        (< 0 (setq dch (load_dialog tmp)))
        (new_dialog "sbz_listbox" dch)
      )
    )
    (princ "\nFehler: Listbox-Dialog konnte nicht geladen werden.")
    )
    (t
      ;; Liste fuellen
      (start_list "list")
      (foreach itm lst (add_list itm))
      (end_list)
      ;; Default-Auswahl: erstes Element
      (set_tile "list" "0")
      (setq rtn "0")
      ;; Filter-Aktion: Liste bei Eingabe neu aufbauen
      (action_tile "filter"
        (strcat
          "(progn"
          "  (start_list \"list\")"
          "  (foreach itm (vl-remove-if-not"
          "    (function (lambda (x) (wcmatch (strcase x) (strcase $value))))"
          "    lst)"
          "    (add_list itm))"
          "  (end_list))"
        )
      )
      ;; Auswahl merken
      (action_tile "list" "(setq rtn $value)")
      ;; Dialog starten
      (setq rtn
        (if (= 1 (start_dialog))
          (mapcar
            '(lambda (x) (nth x lst))
            (read (strcat "(" rtn ")"))
          )
        )
      )
    )
  )
  ;; Cleanup
  (if (and dch (< 0 dch)) (unload_dialog dch))
  (if (and tmp (findfile tmp)) (vl-file-delete tmp))
  rtn
)


;;; ============================================================================
;;; BLOCK-VERARBEITUNG
;;; ============================================================================

;;; --- Font-Anzeigename → TTF-Dateiname ---
(defun SBZ:font-to-ttf (font-name / )
  (cond
    ((= font-name "Arial") "arial.ttf")
    ((= font-name "Arial Bold") "arialbd.ttf")
    ((= font-name "Arial Italic") "ariali.ttf")
    ((= font-name "Arial Bold Italic") "arialbi.ttf")
    ((= font-name "Calibri") "calibri.ttf")
    ((= font-name "Calibri Bold") "calibrib.ttf")
    ((= font-name "Calibri Light") "calibril.ttf")
    ((= font-name "Cambria") "cambria.ttc")
    ((= font-name "Consolas") "consola.ttf")
    ((= font-name "Courier New") "cour.ttf")
    ((= font-name "Courier New Bold") "courbd.ttf")
    ((= font-name "Georgia") "georgia.ttf")
    ((= font-name "Impact") "impact.ttf")
    ((= font-name "Microsoft Sans Serif") "micross.ttf")
    ((= font-name "Palatino Linotype") "pala.ttf")
    ((= font-name "Segoe UI") "segoeui.ttf")
    ((= font-name "Segoe UI Bold") "segoeuib.ttf")
    ((= font-name "Tahoma") "tahoma.ttf")
    ((= font-name "Tahoma Bold") "tahomabd.ttf")
    ((= font-name "Times New Roman") "times.ttf")
    ((= font-name "Times New Roman Bold") "timesbd.ttf")
    ((= font-name "Trebuchet MS") "trebuc.ttf")
    ((= font-name "Trebuchet MS Bold") "trebucbd.ttf")
    ((= font-name "Verdana") "verdana.ttf")
    ((= font-name "Verdana Bold") "verdanab.ttf")
    (T (strcat font-name ".ttf"))  ;; Fallback
  )
)


;;; ----------------------------------------------------------------------------
;;; SBZ:ensure-textstyle
;;; Erstellt einen Text Style fuer die angegebene TTF-Schriftart
;;; Style-Name: "SBZ_<FontName>" (z.B. "SBZ_Arial")
;;; Parameter: font-name - TTF-Schriftname (z.B. "Arial")
;;; Rueckgabe: Style-Name (String)
;;; ----------------------------------------------------------------------------
(defun SBZ:ensure-textstyle (font-name / style-name doc styles style-obj)
  (setq style-name (strcat "SBZ_" font-name))
  (setq doc (vla-get-activedocument (vlax-get-acad-object)))
  (setq styles (vla-get-textstyles doc))
  ;; Pruefen ob Style schon existiert
  (if (vl-catch-all-error-p
        (vl-catch-all-apply 'vla-item (list styles style-name)))
    ;; Nicht vorhanden → erstellen
    (progn
      (setq style-obj (vla-add styles style-name))
      ;; TTF-Dateiname setzen (AutoCAD sucht automatisch in Fonts-Ordner)
      (vl-catch-all-apply 'vla-put-fontFile
        (list style-obj (SBZ:font-to-ttf font-name)))
      (SBZ:log-write "INFO"
        (strcat "Text Style erstellt: '" style-name
                "' → " font-name ".ttf"))
    )
    (SBZ:log-write "DEBUG"
      (strcat "Text Style '" style-name "' existiert bereits"))
  )
  style-name
)

;;; ----------------------------------------------------------------------------
;;; SBZ:get-attr-tags
;;; Liest alle Attribut-Tag-Namen eines Block-Objekts
;;; Parameter: blk-ent - Entity-Name (ename) eines INSERT
;;; Rueckgabe: Liste von Tag-Strings oder nil
;;; ----------------------------------------------------------------------------
(defun SBZ:get-attr-tags (blk-ent / blk-ref attrs tags)
  (setq blk-ref (vlax-ename->vla-object blk-ent))
  (if (= (vla-get-HasAttributes blk-ref) :vlax-true)
    (progn
      (setq attrs (vlax-invoke blk-ref 'GetAttributes))
      (setq tags (mapcar '(lambda (a) (vla-get-TagString a)) attrs))
      tags
    )
    nil
  )
)


;;; ----------------------------------------------------------------------------
;;; SBZ:get-attr-value
;;; Liest den TextString eines bestimmten Attribut-Tags
;;; Parameter:
;;;   blk-ent  - Entity-Name (ename) eines INSERT
;;;   tag-name - Attribut-Tag (String), Case-insensitive
;;; Rueckgabe: TextString oder nil wenn nicht gefunden
;;; ----------------------------------------------------------------------------
(defun SBZ:get-attr-value (blk-ent tag-name / blk-ref attrs result)
  (setq blk-ref (vlax-ename->vla-object blk-ent))
  (if (= (vla-get-HasAttributes blk-ref) :vlax-true)
    (progn
      (setq attrs (vlax-invoke blk-ref 'GetAttributes))
      (foreach attr attrs
        (if (= (strcase (vla-get-TagString attr)) (strcase tag-name))
          (setq result (vla-get-TextString attr))
        )
      )
    )
  )
  result
)


;;; ----------------------------------------------------------------------------
;;; SBZ:parse-height-string
;;; Konvertiert Hoehen-String in Real-Zahl
;;; Behandelt Komma als Dezimaltrenner und optionales + Vorzeichen
;;; Parameter: str - Hoehen-String (z.B. "322,45" oder "+322.45")
;;; Rueckgabe: Real-Zahl oder nil bei ungueltigem String
;;; ----------------------------------------------------------------------------
(defun SBZ:parse-height-string (str / cleaned)
  (if (and str (/= str ""))
    (progn
      ;; Komma durch Punkt ersetzen
      (setq cleaned (vl-string-subst "." "," str))
      ;; Fuehrendes + entfernen
      (if (= (substr cleaned 1 1) "+")
        (setq cleaned (substr cleaned 2))
      )
      ;; Leerzeichen entfernen
      (setq cleaned (vl-string-trim " " cleaned))
      ;; Parsen
      (if (/= cleaned "")
        (atof cleaned)
        nil
      )
    )
    nil
  )
)


;;; ----------------------------------------------------------------------------
;;; SBZ:set-block-z
;;; Setzt die Z-Koordinate eines Blocks via vla-Move
;;; vla-Move verschiebt den INSERT INKLUSIVE aller Attribute!
;;; (entmod auf DXF 10 verschiebt nur den Einfuegepunkt, nicht die ATTRIBs)
;;; Parameter:
;;;   blk-ent - Entity-Name (ename) eines INSERT
;;;   new-z   - Neue Z-Koordinate (Real)
;;; Rueckgabe: T bei Erfolg, nil bei Fehler
;;; ----------------------------------------------------------------------------
(defun SBZ:set-block-z (blk-ent new-z / blk-ref ins-pt old-z delta result)
  (setq blk-ref (vlax-ename->vla-object blk-ent))
  (setq ins-pt (vlax-get blk-ref 'InsertionPoint))
  (if ins-pt
    (progn
      (setq old-z (caddr ins-pt))
      (setq delta (- new-z old-z))
      ;; Nur verschieben wenn tatsaechlich eine Aenderung
      (if (not (equal delta 0.0 1e-6))
        (progn
          (setq result
            (vl-catch-all-apply 'vla-Move
              (list blk-ref
                (vlax-3d-point 0.0 0.0 0.0)
                (vlax-3d-point 0.0 0.0 delta)
              )
            )
          )
          (if (vl-catch-all-error-p result)
            (progn
              (SBZ:log-write "ERROR"
                (strcat "vla-Move fehlgeschlagen: " (vl-catch-all-error-message result)))
              nil
            )
            T
          )
        )
        T ;; Kein Delta = bereits auf richtiger Hoehe
      )
    )
    nil
  )
)


;;; ----------------------------------------------------------------------------
;;; SBZ:set-blockdef-byblock
;;; Setzt Farbe aller Entities in der Block-Definition auf ByBlock
;;; Wird nur EINMAL pro Blockname aufgerufen (nicht pro Instanz!)
;;; Parameter: blk-name - Blockname (String)
;;; ----------------------------------------------------------------------------
(defun SBZ:set-blockdef-byblock (blk-name / blocks blk-def)
  (setq blocks (vla-get-blocks (vla-get-activedocument (vlax-get-acad-object))))
  (if (not (vl-catch-all-error-p
        (setq blk-def (vl-catch-all-apply 'vla-item (list blocks blk-name)))))
    (progn
      (vlax-for obj blk-def
        (vl-catch-all-apply 'vla-put-Color (list obj acByBlock))
      )
      (SBZ:log-write "INFO" (strcat "Block-Definition '" blk-name "': Farbe auf ByBlock gesetzt"))
    )
    (SBZ:log-write "WARN" (strcat "Block-Definition '" blk-name "' nicht gefunden"))
  )
)


;;; ----------------------------------------------------------------------------
;;; SBZ:process-blocks
;;; Kernfunktion: Verarbeitet Blockinstanzen
;;; Parameter:
;;;   blk-name   - Blockname (String)
;;;   attr-tag   - Attribut-Tag fuer Hoehe (String)
;;;   bau0       - Bau-0-Hoehe (Real)
;;;   z-mode     - "ABS" oder "REL" (Z-Koordinate fuer Kopie-Block)
;;;   group-name - Gruppenname (String oder nil)
;;;   sel-set    - Selection Set (ssget Ergebnis, oder nil = alle suchen)
;;; Rueckgabe: Anzahl verarbeiteter Bloecke (Integer)
;;; ----------------------------------------------------------------------------
(defun SBZ:process-blocks (blk-name attr-tag bau0 z-mode group-name sel-set
                           / ss i ent val-str abs-h rel-z ins-z count-ok count-err
                             copy-mode copy-blk-name copy-def-ok target-layer new-ent-name)
  (setq count-ok 0)
  (setq count-err 0)
  ;; Kopie-Modus Variablen lokal cachen
  (setq copy-mode (= *SBZ:cfg-copymode* 1))
  ;; CopyBlock-Name: mit Gruppenname wenn vorhanden
  (setq copy-blk-name
    (if (and group-name (/= group-name ""))
      (SBZ:build-copyblock-name group-name)
      *SBZ:cfg-copyblock*
    )
  )
  (setq target-layer (if (and (= *SBZ:cfg-movelayer* 1)
                               (/= *SBZ:cfg-target-layer* ""))
                       *SBZ:cfg-target-layer* ""))
  ;; Selection Set: uebergeben oder alle suchen
  (setq ss (if sel-set sel-set
    (ssget "X" (list (cons 2 blk-name) (cons 410 "Model")))))
  (if (and ss (> (sslength ss) 0))
    (progn
      (SBZ:log-write "INFO"
        (strcat "Verarbeite " (itoa (sslength ss)) " Bloecke '"
                blk-name "' mit Attribut '" attr-tag
                "', Bau-0=" (rtos bau0 2 3)
                (if copy-mode (strcat ", Kopie-Modus → '" copy-blk-name "'") "")))
      ;; ByBlock auf Block-Definition setzen (einmal, nicht pro Instanz!)
      (if (and (= *SBZ:cfg-byblock* 1) (not copy-mode))
        (SBZ:set-blockdef-byblock blk-name)
      )
      ;; Im Kopie-Modus: Block-Definition sicherstellen
      (setq copy-def-ok T)
      (if copy-mode
        (if (not (SBZ:ensure-copyblock-def copy-blk-name))
          (progn
            (SBZ:log-write "ERROR"
              (strcat "Block-Definition '" copy-blk-name "' konnte nicht erstellt werden"))
            (setq copy-def-ok nil)
          )
        )
      )
      (if copy-def-ok
        (progn
          ;; Dekrementierende Schleife (Lee Mac Performance-Pattern)
          (setq i (sslength ss))
          (while (> (setq i (1- i)) -1)
            (setq ent (ssname ss i))
            ;; Attributwert lesen
            (setq val-str (SBZ:get-attr-value ent attr-tag))
            (if val-str
              (progn
                (setq abs-h (SBZ:parse-height-string val-str))
                (if abs-h
                  (progn
                    ;; Relative Hoehe berechnen (absolut minus Bau-0)
                    (setq rel-z (- abs-h bau0))
                    ;; Z-Koordinate fuer Kopie je nach Modus
                    (setq ins-z (if (= z-mode "ABS") abs-h rel-z))
                    (if copy-mode
                      ;; === KOPIE-MODUS: Original beibehalten, Kopie-Block einfuegen ===
                      (progn
                        (setq new-ent-name
                          (SBZ:insert-copyblock ent copy-blk-name abs-h rel-z ins-z bau0 z-mode group-name))
                        (if new-ent-name
                          (progn
                            ;; XData mit Gruppenname + Quell-Handle setzen
                            (if (and group-name (/= group-name ""))
                              (SBZ:set-xdata
                                (vlax-vla-object->ename new-ent-name)
                                group-name
                                (cdr (assoc 5 (entget ent))))  ;; DXF 5 = Handle des Quell-Blocks
                            )
                            (setq count-ok (1+ count-ok))
                            (SBZ:log-write "DEBUG"
                              (strcat "Block " (itoa (1+ i)) ": Kopie eingefuegt"
                                      " ABS=" (rtos abs-h 2 3)
                                      " REL=" (rtos rel-z 2 3)
                                      " Z=" (rtos ins-z 2 3) " (" z-mode ")"
                                      (if group-name (strcat " Gruppe='" group-name "'") "")))
                          )
                          (progn
                            (setq count-err (1+ count-err))
                            (SBZ:log-write "ERROR"
                              (strcat "Block " (itoa (1+ i)) ": Kopie-Insert fehlgeschlagen"))
                          )
                        )
                      )
                      ;; === STANDARD-MODUS: Original verschieben ===
                      (if (SBZ:set-block-z ent ins-z)
                        (progn
                          (setq count-ok (1+ count-ok))
                          (SBZ:log-write "DEBUG"
                            (strcat "Block " (itoa (1+ i)) ": Attr='" val-str
                                    "' abs=" (rtos abs-h 2 3)
                                    " rel=" (rtos rel-z 2 3)
                                    " Z=" (rtos ins-z 2 3) " (" z-mode ") → verschoben"))
                          ;; Layer verschieben (nur Standard-Modus)
                          (if (/= target-layer "")
                            (vl-catch-all-apply 'vla-put-Layer
                              (list (vlax-ename->vla-object ent) target-layer))
                          )
                        )
                        (progn
                          (setq count-err (1+ count-err))
                          (SBZ:log-write "ERROR"
                            (strcat "Block " (itoa (1+ i)) ": vla-Move fehlgeschlagen"))
                        )
                      )
                    )
                  )
                  (progn
                    (setq count-err (1+ count-err))
                    (SBZ:log-write "WARN"
                      (strcat "Block " (itoa (1+ i))
                              ": Attribut '" val-str "' ist keine gueltige Zahl"))
                  )
                )
              )
              (progn
                (setq count-err (1+ count-err))
                (SBZ:log-write "WARN"
                  (strcat "Block " (itoa (1+ i)) ": Attribut '" attr-tag "' nicht gefunden"))
              )
            )
          ) ;end while
        )
      ) ;end copy-def-ok
      ;; Zusammenfassung
      (SBZ:log-write "INFO"
        (strcat "Fertig: " (itoa count-ok) " OK, " (itoa count-err) " Fehler"))
      (if (> count-err 0)
        (SBZ:log-write "WARN"
          (strcat (itoa count-err) " Bloecke konnten nicht verarbeitet werden (siehe Log)"))
      )
      count-ok
    )
    (progn
      (SBZ:log-write "WARN" (strcat "Keine Bloecke '" blk-name "' im Modelspace gefunden"))
      0
    )
  )
)


;;; ============================================================================
;;; KOPIE-BLOCK: DEFINITION ERSTELLEN + EINFUEGEN
;;; ============================================================================

;;; ----------------------------------------------------------------------------
;;; SBZ:make-filled-quarter
;;; Erstellt gefuellte Viertelkreis-Segmente als SOLID-Faecher innerhalb
;;; einer laufenden Block-Definition (zwischen BLOCK und ENDBLK).
;;; Verwendet Pizza-Slice SOLIDs vom Mittelpunkt zum Kreisrand.
;;; Parameter:
;;;   blk-name   - Blockname (nur fuer Logging)
;;;   radius     - Kreisradius (Real)
;;;   ang-start  - Startwinkel in Radians
;;;   ang-end    - Endwinkel in Radians
;;;   segments   - Anzahl Segmente (8 = gute Approximation)
;;; ----------------------------------------------------------------------------
(defun SBZ:make-filled-quarter (blk-name radius ang-start ang-end segments
                                / i ang-step a1 a2 p1 p2)
  (setq ang-step (/ (- ang-end ang-start) (float segments)))
  (setq i 0)
  (repeat segments
    (setq a1 (+ ang-start (* i ang-step)))
    (setq a2 (+ ang-start (* (1+ i) ang-step)))
    (setq p1 (list (* radius (cos a1)) (* radius (sin a1)) 0.0))
    (setq p2 (list (* radius (cos a2)) (* radius (sin a2)) 0.0))
    ;; SOLID: Dreieck vom Mittelpunkt zu zwei Kreisrand-Punkten
    ;; DXF 10=Ecke1, 11=Ecke2, 12=Ecke3, 13=Ecke4 (=Ecke3 fuer Dreieck)
    (entmake (list '(0 . "SOLID") '(8 . "0")
                   '(62 . 0) '(6 . "ByBlock") '(370 . -2)
                   '(10 0.0 0.0 0.0)     ;; Mittelpunkt
                   (cons 11 p1)           ;; Kreisrand 1
                   (cons 12 p2)           ;; Kreisrand 2
                   (cons 13 p2)           ;; = Ecke3 (Dreieck)
             ))
    (setq i (1+ i))
  )
)


;;; ----------------------------------------------------------------------------
;;; SBZ:ensure-copyblock-def
;;; Erstellt die Block-Definition fuer den Kopie-Block falls nicht vorhanden.
;;; Block enthaelt: Punkt-Marker + 2 Attribute (HOEHE_ABS, HOEHE_REL)
;;; Parameter: blk-name - Blockname (String)
;;; Rueckgabe: T wenn vorhanden/erstellt, nil bei Fehler
;;; ----------------------------------------------------------------------------
(defun SBZ:ensure-copyblock-def (blk-name / blocks blk-exists style-name)
  (setq blocks (vla-get-blocks (vla-get-activedocument (vlax-get-acad-object))))
  ;; Text Style fuer Schriftart sicherstellen
  (setq style-name (SBZ:ensure-textstyle (SBZ:get-font)))
  ;; Pruefen ob Block schon existiert
  (setq blk-exists
    (not (vl-catch-all-error-p
      (vl-catch-all-apply 'vla-item (list blocks blk-name)))))
  (if blk-exists
    (progn
      (SBZ:log-write "DEBUG" (strcat "Block-Definition '" blk-name "' existiert bereits"))
      T
    )
    ;; Block-Definition erstellen via entmake
    (progn
      (SBZ:log-write "INFO" (strcat "Erstelle Block-Definition '" blk-name "'"))
      ;; BLOCK-Header
      (if (entmake (list '(0 . "BLOCK")
                         (cons 2 blk-name)
                         '(10 0.0 0.0 0.0)
                         '(70 . 2)))    ;; Bit 2 = hat Attribute
        (progn
          ;; === Vermessungspunkt: Schachbrett mit Fadenkreuz ===
          ;; Radius 0.05m (Durchmesser 0.1m), Einfuegepunkt = Mitte
          ;; ByBlock Properties fuer alle Entities
          ;; DXF 62=0, DXF 6="ByBlock", DXF 370=-2

          ;; --- Gefuellte Viertelkreise (Schachbrett) ---
          ;; Oben-links (Q2) und unten-rechts (Q4) gefuellt
          ;; Approximiert mit SOLID-Faechern (8 Segmente pro Viertel)
          (SBZ:make-filled-quarter blk-name 0.05  (/ pi 2) pi       8) ;; Q2: oben-links
          (SBZ:make-filled-quarter blk-name 0.05  (* pi 1.5) (* pi 2) 8) ;; Q4: unten-rechts

          ;; --- Kreisumriss ---
          (entmake (list '(0 . "CIRCLE") '(8 . "0")
                        '(62 . 0) '(6 . "ByBlock") '(370 . -2)
                        '(10 0.0 0.0 0.0) '(40 . 0.05)))

          ;; --- Fadenkreuz (ragt ueber Kreis hinaus) ---
          (entmake (list '(0 . "LINE") '(8 . "0")
                        '(62 . 0) '(6 . "ByBlock") '(370 . -2)
                        '(10 -0.08 0.0 0.0) '(11 0.08 0.0 0.0)))
          (entmake (list '(0 . "LINE") '(8 . "0")
                        '(62 . 0) '(6 . "ByBlock") '(370 . -2)
                        '(10 0.0 -0.08 0.0) '(11 0.0 0.08 0.0)))

          ;; --- Trennlinien (horizontale und vertikale Achse im Kreis) ---
          ;; Nicht noetig — Fadenkreuz + Kreis reichen als Trennung

          ;; ATTDEF: HOEHE_ABS (absolut) — sichtbar, rechts vom Marker
          ;; Justierung: Links Unten (72=0, 74=1) → Text waechst nach oben
          ;; DXF 10 = Startpunkt, DXF 11 = Ausrichtungspunkt (bei Justierung)
          ;; Position: rechts vom Kreis, leicht ueber Mittellinie
          (entmake (list '(0 . "ATTDEF")
                        '(8 . "0")
                        '(62 . 0) '(6 . "ByBlock") '(370 . -2)
                        (cons 7 style-name)    ;; Text Style (Schriftart)
                        '(10 0.1 0.02 0.0)    ;; Startpunkt (Y = halbe Texthoehe ueber Mitte)
                        '(11 0.1 0.02 0.0)    ;; Ausrichtungspunkt
                        '(40 . 0.07)          ;; Texthoehe (wird beim Insert skaliert)
                        '(1 . "0.000")
                        '(2 . "HOEHE_ABS")
                        '(3 . "Absolute Hoehe")
                        '(70 . 16)            ;; Flags: sichtbar + Position gesperrt
                        '(72 . 0)             ;; Horizontale Justierung: Links
                        '(74 . 1)             ;; Vertikale Justierung: Unten
                  ))
          ;; ATTDEF: HOEHE_REL (relativ) — sichtbar, rechts vom Marker
          ;; Justierung: Links Oben (72=0, 74=3) → Text waechst nach unten
          ;; Position: rechts vom Kreis, leicht unter Mittellinie
          (entmake (list '(0 . "ATTDEF")
                        '(8 . "0")
                        '(62 . 0) '(6 . "ByBlock") '(370 . -2)
                        (cons 7 style-name)
                        '(10 0.1 -0.02 0.0)
                        '(11 0.1 -0.02 0.0)
                        '(40 . 0.07)
                        '(1 . "0.000")
                        '(2 . "HOEHE_REL")
                        '(3 . "Relative Hoehe (nach Bau-0)")
                        '(70 . 16)            ;; Flags: sichtbar + Position gesperrt
                        '(72 . 0)             ;; Links
                        '(74 . 3)             ;; Oben
                  ))
          ;; ATTDEF: HOEHE_BAU0 (Bau-0-Hoehe) — unsichtbar, unter HOEHE_REL
          ;; Justierung: Links Oben (72=0, 74=3)
          ;; Position: REL.Y - 1.7*Texthoehe = -0.02 - 0.119 ≈ -0.14
          ;; ABS=+0.02, REL=-0.02, BAU0=-0.14
          (entmake (list '(0 . "ATTDEF")
                        '(8 . "0")
                        '(62 . 0) '(6 . "ByBlock") '(370 . -2)
                        (cons 7 style-name)
                        '(10 0.1 -0.14 0.0)
                        '(11 0.1 -0.14 0.0)
                        '(40 . 0.07)
                        '(1 . "0.000")
                        '(2 . "HOEHE_BAU0")
                        '(3 . "Bau-0-Hoehe")
                        '(70 . 16)            ;; Flags: sichtbar + Position gesperrt (Layer steuert Sichtbarkeit)
                        '(72 . 0)             ;; Links
                        '(74 . 3)             ;; Oben
                  ))
          ;; ENDBLK
          (if (entmake '((0 . "ENDBLK")))
            (progn
              (SBZ:log-write "INFO" (strcat "Block-Definition '" blk-name "' erstellt"))
              T
            )
            (progn
              (SBZ:log-write "ERROR" (strcat "ENDBLK fehlgeschlagen fuer '" blk-name "'"))
              nil
            )
          )
        )
        (progn
          (SBZ:log-write "ERROR" (strcat "BLOCK-Header fehlgeschlagen fuer '" blk-name "'"))
          nil
        )
      )
    )
  )
)


;;; ----------------------------------------------------------------------------
;;; SBZ:ensure-layer
;;; Erstellt Layer falls nicht vorhanden
;;; Parameter: layer-name - Layername (String)
;;; ----------------------------------------------------------------------------
(defun SBZ:ensure-layer (layer-name / doc layers)
  (setq doc (vla-get-activedocument (vlax-get-acad-object)))
  (setq layers (vla-get-layers doc))
  (if (vl-catch-all-error-p
        (vl-catch-all-apply 'vla-item (list layers layer-name)))
    (progn
      (vla-add layers layer-name)
      (SBZ:log-write "INFO" (strcat "Layer erstellt: '" layer-name "'"))
    )
  )
  layer-name
)


;;; ----------------------------------------------------------------------------
;;; SBZ:ensure-layer-with-freeze
;;; Erstellt Layer falls nicht vorhanden und setzt Freeze-Status
;;; Parameter:
;;;   layer-name - Layername (String)
;;;   freeze     - 0 = thawed (sichtbar), 1 = frozen (unsichtbar)
;;; ----------------------------------------------------------------------------
(defun SBZ:ensure-layer-with-freeze (layer-name freeze / doc layers lay-obj)
  (setq doc (vla-get-activedocument (vlax-get-acad-object)))
  (setq layers (vla-get-layers doc))
  ;; Layer erstellen falls nicht vorhanden
  (if (vl-catch-all-error-p
        (setq lay-obj (vl-catch-all-apply 'vla-item (list layers layer-name))))
    (progn
      (setq lay-obj (vla-add layers layer-name))
      (SBZ:log-write "INFO" (strcat "Layer erstellt: '" layer-name "'"))
    )
  )
  ;; Freeze/Thaw setzen (aktuellen Layer kann man nicht einfrieren)
  (if (and lay-obj (/= (strcase layer-name) (strcase (getvar "CLAYER"))))
    (vl-catch-all-apply 'vla-put-Freeze
      (list lay-obj (if (= freeze 1) :vlax-true :vlax-false)))
  )
  layer-name
)


;;; ----------------------------------------------------------------------------
;;; SBZ:ensure-attr-layers
;;; Erstellt die 3 Attribut-Sub-Layer fuer einen Block-Layer
;;; Layer-Schema: <base>-AttABS, <base>-AttREL, <base>-AttBAU0
;;; Setzt Initial-Freeze je nach Config-Toggles
;;; Parameter: base-layer - Basis-Layername (z.B. "VM_HP_STAB137")
;;; ----------------------------------------------------------------------------
(defun SBZ:ensure-attr-layers (base-layer / )
  ;; Basis-Layer (fuer Block-Symbol)
  (SBZ:ensure-layer base-layer)
  ;; Attribut-Sub-Layer mit Freeze-Status
  (SBZ:ensure-layer-with-freeze
    (strcat base-layer "-AttABS") *SBZ:cfg-freeze-abs*)
  (SBZ:ensure-layer-with-freeze
    (strcat base-layer "-AttREL") *SBZ:cfg-freeze-rel*)
  (SBZ:ensure-layer-with-freeze
    (strcat base-layer "-AttBAU0") *SBZ:cfg-freeze-bau0*)
  (SBZ:log-write "INFO"
    (strcat "Attribut-Layer erstellt: " base-layer
            "-AttABS(" (if (= *SBZ:cfg-freeze-abs* 1) "frozen" "thawed") ")"
            " -AttREL(" (if (= *SBZ:cfg-freeze-rel* 1) "frozen" "thawed") ")"
            " -AttBAU0(" (if (= *SBZ:cfg-freeze-bau0* 1) "frozen" "thawed") ")"))
)


;;; ----------------------------------------------------------------------------
;;; SBZ:get-copy-layername
;;; Berechnet den Layer-Namen fuer Vermessungs-Hoehenpunkte
;;; Format: VM_<Gruppe>_<Gruppenname>  (ÖNORM A 6241 angelehnt)
;;; VM = Vermessung (Fachbereich), Gruppe = HP/GP/GE/FP (Gegenstandsgruppe)
;;; Parameter:
;;;   z-mode     - "ABS" oder "REL" (nicht fuer Layer-Name verwendet)
;;;   bau0       - Bau-0-Hoehe (Real, nicht fuer Layer-Name verwendet)
;;;   group-name - Gruppenname (String, oder nil)
;;; Rueckgabe: Layer-Name (z.B. "VM_HP_STAB137")
;;; ----------------------------------------------------------------------------
(defun SBZ:get-copy-layername (z-mode bau0 group-name / grp)
  (setq grp *SBZ:cfg-copylayer*)
  (if (and group-name (/= group-name ""))
    (strcat "VM_" grp "_" group-name)
    (strcat "VM_" grp)
  )
)


;;; ----------------------------------------------------------------------------
;;; SBZ:insert-copyblock
;;; Fuegt den Kopie-Block an der Position des Original-Blocks ein
;;; Parameter:
;;;   orig-ent    - Entity-Name des Original-Blocks (ename)
;;;   blk-name    - Name des Kopie-Blocks (String)
;;;   abs-h       - Absolute Hoehe (Real, fuer Attribut-Text)
;;;   rel-z       - Relative Hoehe nach Bau-0 (Real, fuer Attribut-Text)
;;;   ins-z       - Z-Koordinate fuer Block-Insert (Real, ABS oder REL je nach Modus)
;;;   bau0        - Bau-0-Hoehe (Real, fuer HOEHE_BAU0 Attribut)
;;;   z-mode      - "ABS" oder "REL"
;;;   group-name  - Gruppenname (String oder nil, fuer Layer-Name)
;;; Rueckgabe: VLA-Objekt bei Erfolg, nil bei Fehler
;;; ----------------------------------------------------------------------------
(defun SBZ:insert-copyblock (orig-ent blk-name abs-h rel-z ins-z bau0 z-mode group-name
                             / orig-data orig-pt ins-pt new-ent attrs bks-angle
                               scale suffix copy-layer style-name
                               abs-str rel-str bau0-str tag-str
                               att-ent att-data)
  ;; XY vom Original, Z = je nach Modus (ABS oder REL)
  (setq orig-data (entget orig-ent))
  (setq orig-pt (cdr (assoc 10 orig-data)))
  (setq ins-pt (list (car orig-pt) (cadr orig-pt) ins-z))
  ;; Einstellungen lesen
  (setq scale (SBZ:get-scale))
  (setq suffix (SBZ:get-suffix))
  ;; Text Style sicherstellen
  (setq style-name (SBZ:ensure-textstyle (SBZ:get-font)))
  ;; Layer: V_<Layer>_<Gruppenname> + Attribut-Sub-Layer
  (setq copy-layer (SBZ:get-copy-layername z-mode bau0 group-name))
  (SBZ:ensure-attr-layers copy-layer)
  ;; Block einfuegen
  ;; BKS-Rotation berechnen: Winkel der UCS X-Achse im WKS
  ;; Damit Block-Text parallel zum aktuellen BKS steht
  (setq bks-angle
    (angle '(0.0 0.0 0.0) (getvar "UCSXDIR")))
  ;; Block einfuegen (mit BKS-Rotation)
  (setq new-ent
    (vl-catch-all-apply
      '(lambda ()
        (vla-InsertBlock
          (vla-get-modelspace (vla-get-activedocument (vlax-get-acad-object)))
          (vlax-3d-point ins-pt)
          blk-name
          scale scale scale
          bks-angle
        )
      )
    )
  )
  (if (vl-catch-all-error-p new-ent)
    (progn
      (SBZ:log-write "ERROR"
        (strcat "Kopie-Block Insert fehlgeschlagen: " (vl-catch-all-error-message new-ent)))
      nil
    )
    (progn
      ;; Absolut-Hoehe: Wert + Suffix
      (setq abs-str (strcat (SBZ:rtos-fixed abs-h 2)
                            (if (and suffix (/= suffix ""))
                              (strcat " " suffix) "")))
      ;; Relativ-Hoehe: Vorzeichen + Wert
      (cond
        ((> rel-z 0.001)  (setq rel-str (strcat "+" (SBZ:rtos-fixed rel-z 2))))
        ((< rel-z -0.001) (setq rel-str (SBZ:rtos-fixed rel-z 2)))
        (T                (setq rel-str (strcat "%%P" (SBZ:rtos-fixed (abs rel-z) 2))))
      )
      ;; Bau-0 Zeile: "±0.00 = <Bau-0-Hoehe> <Suffix>"
      ;; Zeigt die Bau-0-Hoehe als fixe Info (gleich fuer ALLE Bloecke!)
      ;; ±0.00 ist symbolisch (= Nulllinie), dahinter der eingegebene Bau-0-Wert
      (setq bau0-str (strcat "%%P0.00 = " (SBZ:rtos-fixed bau0 2)
                             (if (and suffix (/= suffix ""))
                               (strcat " " suffix) "")))
      ;; Attribute: Text setzen + Layer per entmod (DXF 8)
      ;; Positionen bleiben aus Block-Definition (Skalierung regelt Groesse)
      ;; Sichtbarkeit ueber Layer Freeze/Thaw, nicht Invisible-Flag
      (setq attrs (vlax-invoke new-ent 'GetAttributes))
      (foreach attr attrs
        (setq tag-str (strcase (vla-get-TagString attr)))
        (setq att-ent (vlax-vla-object->ename attr))
        (setq att-data (entget att-ent))
        (cond
          ((= tag-str "HOEHE_ABS")
            (setq att-data (subst (cons 1 abs-str) (assoc 1 att-data) att-data))
            (setq att-data (subst (cons 70 16) (assoc 70 att-data) att-data))
            (setq att-data (subst (cons 7 style-name) (assoc 7 att-data) att-data))
            (setq att-data (subst (cons 8 (strcat copy-layer "-AttABS"))
                                  (assoc 8 att-data) att-data))
            ;; Farbe: 0=ByBlock (Default), sonst ACI-Code
            (if (/= *SBZ:cfg-color-abs* 0)
              (setq att-data (subst (cons 62 *SBZ:cfg-color-abs*) (assoc 62 att-data) att-data)))
            (entmod att-data) (entupd att-ent)
          )
          ((= tag-str "HOEHE_REL")
            (setq att-data (subst (cons 1 rel-str) (assoc 1 att-data) att-data))
            (setq att-data (subst (cons 70 16) (assoc 70 att-data) att-data))
            (setq att-data (subst (cons 7 style-name) (assoc 7 att-data) att-data))
            (setq att-data (subst (cons 8 (strcat copy-layer "-AttREL"))
                                  (assoc 8 att-data) att-data))
            (if (/= *SBZ:cfg-color-rel* 0)
              (setq att-data (subst (cons 62 *SBZ:cfg-color-rel*) (assoc 62 att-data) att-data)))
            (entmod att-data) (entupd att-ent)
          )
          ((= tag-str "HOEHE_BAU0")
            (setq att-data (subst (cons 1 bau0-str) (assoc 1 att-data) att-data))
            (setq att-data (subst (cons 70 16) (assoc 70 att-data) att-data))
            (setq att-data (subst (cons 7 style-name) (assoc 7 att-data) att-data))
            (setq att-data (subst (cons 8 (strcat copy-layer "-AttBAU0"))
                                  (assoc 8 att-data) att-data))
            (if (/= *SBZ:cfg-color-bau0* 0)
              (setq att-data (subst (cons 62 *SBZ:cfg-color-bau0*) (assoc 62 att-data) att-data)))
            (entmod att-data) (entupd att-ent)
          )
        )
      )
      ;; Block-Symbol auf Kopie-Layer
      (vl-catch-all-apply 'vla-put-Layer (list new-ent copy-layer))
      ;; Block-Farbe setzen (ACI-Code)
      (vl-catch-all-apply 'vla-put-Color (list new-ent *SBZ:cfg-color-block*))
      (SBZ:log-write "DEBUG"
        (strcat "Kopie-Block: ABS='" abs-str "' REL='" rel-str
                "' Layer='" copy-layer "'"))
      new-ent  ;; VLA-Objekt zurueckgeben (fuer XData)
    )
  )
)


;;; ----------------------------------------------------------------------------
;;; SBZ:update-existing-blocks
;;; Aktualisiert alle bestehenden Kopie-Bloecke mit den aktuellen Settings:
;;; Schriftart (DXF 7), Farbe (DXF 62), Layer (DXF 8), Block-Farbe
;;; Aendert NICHT die Hoehenwerte — nur visuelle Einstellungen.
;;; Rueckgabe: Anzahl aktualisierter Bloecke
;;; ----------------------------------------------------------------------------
(defun SBZ:update-existing-blocks ( / blk-name style-name ss i ent
                                      blk-ref attrs att-ent att-data tag-str
                                      copy-layer count)
  (setq blk-name *SBZ:cfg-copyblock*)
  (setq style-name (SBZ:ensure-textstyle (SBZ:get-font)))
  (setq count 0)
  ;; Alle Kopie-Bloecke im Modelspace suchen
  (setq ss (ssget "X" (list (cons 2 blk-name) (cons 410 "Model"))))
  (if (and ss (> (sslength ss) 0))
    (progn
      (SBZ:log-write "INFO"
        (strcat "Update: " (itoa (sslength ss)) " '" blk-name "' Bloecke gefunden"))
      ;; Dekrementierende Schleife
      (setq i (sslength ss))
      (while (> (setq i (1- i)) -1)
        (setq ent (ssname ss i))
        (setq blk-ref (vlax-ename->vla-object ent))
        ;; Block-Farbe setzen
        (vl-catch-all-apply 'vla-put-Color (list blk-ref *SBZ:cfg-color-block*))
        ;; Attribute durchlaufen
        (setq attrs (vlax-invoke blk-ref 'GetAttributes))
        (foreach attr attrs
          (setq tag-str (strcase (vla-get-TagString attr)))
          (setq att-ent (vlax-vla-object->ename attr))
          (setq att-data (entget att-ent))
          ;; Layer-Name vom aktuellen Attribut-Layer ableiten
          ;; Bestehender Layer = aktueller DXF 8 Wert → Basis extrahieren
          (setq copy-layer (cdr (assoc 8 (entget ent))))
          (cond
            ((= tag-str "HOEHE_ABS")
              ;; Schriftart
              (if (assoc 7 att-data)
                (setq att-data (subst (cons 7 style-name) (assoc 7 att-data) att-data))
                (setq att-data (append att-data (list (cons 7 style-name))))
              )
              ;; Farbe
              (if (/= *SBZ:cfg-color-abs* 0)
                (if (assoc 62 att-data)
                  (setq att-data (subst (cons 62 *SBZ:cfg-color-abs*) (assoc 62 att-data) att-data))
                  (setq att-data (append att-data (list (cons 62 *SBZ:cfg-color-abs*))))
                )
                ;; Von Block: Farbe auf 0 (ByBlock)
                (if (assoc 62 att-data)
                  (setq att-data (subst (cons 62 0) (assoc 62 att-data) att-data))
                )
              )
              ;; Layer
              (setq att-data (subst (cons 8 (strcat copy-layer "-AttABS"))
                                    (assoc 8 att-data) att-data))
              (entmod att-data) (entupd att-ent)
            )
            ((= tag-str "HOEHE_REL")
              (if (assoc 7 att-data)
                (setq att-data (subst (cons 7 style-name) (assoc 7 att-data) att-data))
                (setq att-data (append att-data (list (cons 7 style-name))))
              )
              (if (/= *SBZ:cfg-color-rel* 0)
                (if (assoc 62 att-data)
                  (setq att-data (subst (cons 62 *SBZ:cfg-color-rel*) (assoc 62 att-data) att-data))
                  (setq att-data (append att-data (list (cons 62 *SBZ:cfg-color-rel*))))
                )
                (if (assoc 62 att-data)
                  (setq att-data (subst (cons 62 0) (assoc 62 att-data) att-data))
                )
              )
              (setq att-data (subst (cons 8 (strcat copy-layer "-AttREL"))
                                    (assoc 8 att-data) att-data))
              (entmod att-data) (entupd att-ent)
            )
            ((= tag-str "HOEHE_BAU0")
              (if (assoc 7 att-data)
                (setq att-data (subst (cons 7 style-name) (assoc 7 att-data) att-data))
                (setq att-data (append att-data (list (cons 7 style-name))))
              )
              (if (/= *SBZ:cfg-color-bau0* 0)
                (if (assoc 62 att-data)
                  (setq att-data (subst (cons 62 *SBZ:cfg-color-bau0*) (assoc 62 att-data) att-data))
                  (setq att-data (append att-data (list (cons 62 *SBZ:cfg-color-bau0*))))
                )
                (if (assoc 62 att-data)
                  (setq att-data (subst (cons 62 0) (assoc 62 att-data) att-data))
                )
              )
              (setq att-data (subst (cons 8 (strcat copy-layer "-AttBAU0"))
                                    (assoc 8 att-data) att-data))
              (entmod att-data) (entupd att-ent)
            )
          )
        )
        (setq count (1+ count))
      )
      (SBZ:log-write "INFO" (strcat "Update: " (itoa count) " Bloecke aktualisiert"))
    )
    (SBZ:log-write "INFO" (strcat "Update: Keine '" blk-name "' Bloecke gefunden"))
  )
  count
)


;;; ============================================================================
;;; BEFEHLE
;;; ============================================================================

;;; ----------------------------------------------------------------------------
;;; c:SETBLOCKZ - Hauptbefehl
;;; Workflow:
;;;   1. Block anklicken → Blockname + Attribute ermitteln
;;;   2. Attribut fuer Hoehe waehlen (Filter-Listbox)
;;;   3. Bau-0-Hoehe: aus Custom Property oder User-Eingabe
;;;   4. Alle Instanzen verarbeiten (Z setzen)
;;;   5. Optional: ByBlock, Layer verschieben
;;; ----------------------------------------------------------------------------
(defun c:SETBLOCKZ ( / *error* old-cmdecho
                       sel blk-ent blk-name attr-tags selected-attr
                       bau0 bau0-input bau0-str dwg-bau0 ss-preview ss-work
                       ss-filtered i ent ent-data
                       num-found confirm sel-mode
                       z-mode count group-name)
  (SBZ:ensure-init)
  ;; Lokaler Error-Handler
  (defun *error* (msg)
    (if (not (SBZ:cancel-p msg))
      (progn
        (princ (strcat "\nFehler: " msg))
        (SBZ:log-write "ERROR" (strcat "SETBLOCKZ Error-Handler: " msg))
      )
      (SBZ:log-write "INFO" "SETBLOCKZ: Abbruch durch User")
    )
    ;; Markierung aufheben falls aktiv
    (sssetfirst nil nil)
    (if old-cmdecho (setvar "CMDECHO" old-cmdecho))
    (princ)
  )
  ;; Systemvariablen sichern
  (setq old-cmdecho (getvar "CMDECHO"))
  (setvar "CMDECHO" 0)

  (SBZ:log-write "INFO" "Befehl SETBLOCKZ gestartet")

  ;; --- Schritt 1: Block auswaehlen ---
  (setq sel (entsel "\nBlock waehlen (Referenz fuer Blockname + Attribute): "))
  (if (not sel)
    (progn
      (princ "\nKein Objekt gewaehlt.")
      (SBZ:log-write "INFO" "Kein Objekt gewaehlt, Abbruch")
      (setvar "CMDECHO" old-cmdecho)
      (princ)
    )
    (progn
      (setq blk-ent (car sel))
      ;; Pruefen ob INSERT (Block)
      (if (/= (cdr (assoc 0 (entget blk-ent))) "INSERT")
        (progn
          (princ "\nGewaeltes Objekt ist kein Block.")
          (SBZ:log-write "WARN" "Gewaehltes Objekt ist kein Block")
          (setvar "CMDECHO" old-cmdecho)
          (princ)
        )
        (progn
          ;; Blockname ermitteln (EffectiveName fuer dynamische Bloecke)
          (setq blk-name (cdr (assoc 2 (entget blk-ent))))
          (SBZ:log-write "INFO" (strcat "Block gewaehlt: '" blk-name "'"))

          ;; --- Schritt 2: Attribut-Tags lesen ---
          (setq attr-tags (SBZ:get-attr-tags blk-ent))
          (if (not attr-tags)
            (progn
              (princ (strcat "\nBlock '" blk-name "' hat keine Attribute."))
              (SBZ:log-write "WARN" (strcat "Block '" blk-name "' hat keine Attribute"))
              (setvar "CMDECHO" old-cmdecho)
              (princ)
            )
            (progn
              (SBZ:log-write "INFO"
                (strcat "Attribute gefunden: " (vl-princ-to-string attr-tags)))

              ;; --- Schritt 3: Attribut waehlen (Filter-Listbox) ---
              (setq selected-attr (car (SBZ:filtlistbox "Attribut fuer Hoehenwert waehlen" attr-tags nil)))
              (if (not selected-attr)
                (progn
                  (princ "\nKein Attribut gewaehlt.")
                  (SBZ:log-write "INFO" "Kein Attribut gewaehlt, Abbruch")
                  (setvar "CMDECHO" old-cmdecho)
                  (princ)
                )
                (progn
                  (SBZ:log-write "INFO" (strcat "Attribut gewaehlt: '" selected-attr "'"))

                  ;; --- Schritt 4: Bau-0-Hoehe ---
                  ;; Zuerst aus Custom Property lesen
                  (setq bau0 (SBZ:get-bau0))
                  ;; DWG-Standard merken (fuer Gruppen-Vergleich spaeter)
                  (setq dwg-bau0 (if bau0 bau0 0.0))
                  (if bau0
                    ;; Custom Property vorhanden → anzeigen, aenderbar
                    (progn
                      (princ (strcat "\nBau-0-Hoehe aus Zeichnung: " (rtos bau0 2 3)))
                      (SBZ:log-write "INFO" (strcat "Bau-0 aus DWG: " (rtos bau0 2 3)))
                      (initget "Aendern")
                      (setq bau0-input
                        (getreal (strcat "\nBau-0-Hoehe [" (rtos bau0 2 3)
                                         "] <Enter = beibehalten> [Aendern]: ")))
                      (cond
                        ((= bau0-input "Aendern")
                          (setq bau0 (getreal "\nNeue Bau-0-Hoehe eingeben: "))
                          (if bau0
                            (progn
                              (SBZ:set-bau0 bau0)
                              (SBZ:log-write "INFO" (strcat "Bau-0 geaendert auf: " (rtos bau0 2 3)))
                            )
                            (progn
                              (princ "\nUngueltige Eingabe, Abbruch.")
                              (setvar "CMDECHO" old-cmdecho)
                              (princ)
                            )
                          )
                        )
                        ((numberp bau0-input)
                          ;; User hat direkt neue Zahl eingegeben
                          (setq bau0 bau0-input)
                          (SBZ:set-bau0 bau0)
                          (SBZ:log-write "INFO" (strcat "Bau-0 geaendert auf: " (rtos bau0 2 3)))
                        )
                        ;; nil = Enter = beibehalten
                      )
                    )
                    ;; Keine Custom Property → User muss eingeben
                    (progn
                      (princ "\nKeine Bau-0-Hoehe in Zeichnung gespeichert.")
                      (setq bau0 (getreal "\nBau-0-Hoehe eingeben (0 = absolute Hoehen): "))
                      (if (not bau0) (setq bau0 0.0))
                      (SBZ:set-bau0 bau0)
                      (SBZ:log-write "INFO" (strcat "Bau-0 neu gesetzt: " (rtos bau0 2 3)))
                    )
                  )

                  ;; --- Schritt 5: Auswahl-Modus ---
                  (if bau0
                    (progn
                      ;; Zuerst alle zaehlen (fuer Anzeige)
                      (setq ss-preview (ssget "X" (list (cons 2 blk-name) (cons 410 "Model"))))
                      (setq num-found (if (and ss-preview (> (sslength ss-preview) 0))
                                        (sslength ss-preview) 0))
                      (sssetfirst nil nil) ;; Keine Markierung vorab

                      (if (= num-found 0)
                        (progn
                          (princ (strcat "\nKeine Bloecke '" blk-name "' im Modelspace gefunden."))
                          (SBZ:log-write "WARN" (strcat "Keine Bloecke '" blk-name "' im Modelspace"))
                        )
                        (progn
                          (SBZ:log-write "INFO"
                            (strcat (itoa num-found) " Bloecke '" blk-name "' im Modelspace"))

                          ;; Auswahl-Modus abfragen
                          (initget "Fortfahren Waehlen Abbruch")
                          (setq sel-mode
                            (getkword
                              (strcat "\n" (itoa num-found) " Bloecke '" blk-name
                                      "' gefunden. [Fortfahren/Waehlen/Abbruch] <Fortfahren>: ")))
                          (if (not sel-mode) (setq sel-mode "Fortfahren"))
                          (SBZ:log-write "INFO" (strcat "Auswahl-Modus: " sel-mode))

                          ;; Selection Set je nach Modus erstellen
                          (setq ss-work nil)
                          (cond
                            ;; --- FORTFAHREN: Alle Bloecke ---
                            ((= sel-mode "Fortfahren")
                              (setq ss-work ss-preview)
                            )

                            ;; --- WAEHLEN: User waehlt einzeln oder Fenster ---
                            ((= sel-mode "Waehlen")
                              (princ (strcat "\nBloecke '" blk-name "' waehlen (Klick/Fenster, Enter = Ende): "))
                              ;; Interaktives ssget OHNE Filter (sonst kein Picking!)
                              ;; AutoCAD zeigt nur INSERT-Entities als waehlbar
                              (setq ss-work (ssget))
                              ;; Nachtraeglich filtern: nur passende Bloecke behalten
                              (if (and ss-work (> (sslength ss-work) 0))
                                (progn
                                  ;; Neues SS mit nur passenden Bloecken
                                  (setq ss-filtered (ssadd))
                                  (setq i (sslength ss-work))
                                  (while (> (setq i (1- i)) -1)
                                    (setq ent (ssname ss-work i))
                                    (setq ent-data (entget ent))
                                    (if (and (= (cdr (assoc 0 ent-data)) "INSERT")
                                             (= (strcase (cdr (assoc 2 ent-data))) (strcase blk-name))
                                             (= (cdr (assoc 410 ent-data)) "Model"))
                                      (ssadd ent ss-filtered)
                                    )
                                  )
                                  (if (> (sslength ss-filtered) 0)
                                    (progn
                                      (setq ss-work ss-filtered)
                                      (SBZ:log-write "INFO"
                                        (strcat "Waehlen: " (itoa (sslength ss-work)) " passende Bloecke"))
                                    )
                                    (progn
                                      (princ (strcat "\nKeine '" blk-name "' Bloecke in der Auswahl."))
                                      (SBZ:log-write "INFO" "Waehlen: Keine passenden Bloecke in Auswahl")
                                      (setq ss-work nil)
                                    )
                                  )
                                )
                                (progn
                                  (princ "\nKeine Objekte gewaehlt.")
                                  (SBZ:log-write "INFO" "Waehlen: Keine Auswahl")
                                  (setq ss-work nil)
                                )
                              )
                            )

                            ;; --- ABBRUCH ---
                            ((= sel-mode "Abbruch")
                              (princ "\nAbgebrochen.")
                              (SBZ:log-write "INFO" "Auswahl abgebrochen")
                            )
                          )

                          ;; --- Schritt 6: Verarbeitung (wenn Selection Set vorhanden) ---
                          (if (and ss-work (> (sslength ss-work) 0))
                            (progn
                              ;; Markieren
                              (setq num-found (sslength ss-work))
                              (sssetfirst nil ss-work)
                              (princ (strcat "\n" (itoa num-found) " Bloecke ausgewaehlt."))
                              (SBZ:log-write "INFO"
                                (strcat (itoa num-found) " Bloecke ausgewaehlt"))

                              ;; Z-Koordinate waehlen
                              (if (equal bau0 0.0 0.001)
                                (progn
                                  (setq z-mode "ABS")
                                  (SBZ:log-write "INFO" "Z-Modus: ABS (Bau-0=0)")
                                )
                                (progn
                                  (initget 1 "Absolut Relativ")
                                  (setq z-mode
                                    (getkword "\nZ-Koordinate? [Absolut/Relativ]: "))
                                  (setq z-mode (if (= z-mode "Absolut") "ABS" "REL"))
                                  (SBZ:log-write "INFO" (strcat "Z-Modus: " z-mode))
                                )
                              )

                              ;; Markierung aufheben
                              (sssetfirst nil nil)

                              ;; Blockname + Attribut merken
                              (SBZ:set-last-blockname blk-name)
                              (SBZ:set-last-attrtag selected-attr)
                              (SBZ:save-config)

                              ;; --- Schritt 7: Gruppenname abfragen ---
                              (setq group-name
                                (getstring T
                                  (strcat "\nGruppenname eingeben <" blk-name ">: ")))
                              (if (or (not group-name) (= group-name ""))
                                (setq group-name blk-name)
                              )
                              ;; Pruefen ob Gruppe schon existiert
                              (if (SBZ:load-group group-name)
                                (progn
                                  (initget 1 "Ueberschreiben Hinzufuegen Abbrechen")
                                  (setq confirm
                                    (getkword
                                      (strcat "\nGruppe '" group-name
                                              "' existiert. [Ueberschreiben/Hinzufuegen/Abbrechen]: ")))
                                  (SBZ:log-write "INFO"
                                    (strcat "Gruppe existiert → User: " confirm))
                                  (cond
                                    ((= confirm "Abbrechen")
                                      (princ "\nAbgebrochen.")
                                      (setq group-name nil)
                                    )
                                    ((= confirm "Ueberschreiben")
                                      (SBZ:log-write "INFO"
                                        (strcat "Gruppe '" group-name "' wird ueberschrieben"))
                                      (SBZ:delete-group group-name)
                                    )
                                    ((= confirm "Hinzufuegen")
                                      (SBZ:log-write "INFO"
                                        (strcat "Bloecke werden zu Gruppe '" group-name "' hinzugefuegt"))
                                    )
                                  )
                                )
                              )

                              ;; --- Schritt 8: Verarbeitung ---
                              (if group-name
                                (progn
                                  (SBZ:log-write "INFO"
                                    (strcat "Gruppe: '" group-name "'"))
                                  (setq count
                                    (SBZ:process-blocks blk-name selected-attr bau0
                                      z-mode group-name ss-work))
                                  (princ (strcat "\n" (itoa count) " Bloecke verarbeitet."))

                                  ;; Gruppe als XRecord speichern
                                  (setq bau0-str
                                    (if (equal bau0 dwg-bau0 0.001)
                                      ""
                                      (rtos bau0 2 3)
                                    )
                                  )
                                  (SBZ:save-group group-name
                                    (SBZ:group-data-from-current
                                      blk-name selected-attr bau0-str z-mode group-name))
                                  (princ (strcat "\nGruppe '" group-name "' gespeichert."))
                                )
                              )
                            )
                          )
                        )
                      )
                    )
                  )
                ) ;end selected-attr progn
              ) ;end selected-attr if
            ) ;end attr-tags progn
          ) ;end attr-tags if
        ) ;end INSERT progn
      ) ;end INSERT if
    ) ;end sel progn
  ) ;end sel if

  ;; Cleanup
  (if old-cmdecho (setvar "CMDECHO" old-cmdecho))
  (SBZ:log-write "INFO" "Befehl SETBLOCKZ beendet")
  (princ)
)


;;; ----------------------------------------------------------------------------
;;; c:SBZSETTINGS - Einstellungen-Dialog
;;; DCL mit: Bau-0, ByBlock Toggle, Layer Toggle + Auswahl,
;;;          letzte Verarbeitung anzeigen, Neu berechnen Button
;;; ----------------------------------------------------------------------------

;;; --- Gaengige TTF-Schriftarten (kuratierte Liste) ---
;;; Rueckgabe: Liste von Font-Namen (ohne .ttf Extension)
(defun SBZ:get-font-list ( / )
  (list
    "Arial"
    "Arial Bold"
    "Arial Italic"
    "Arial Bold Italic"
    "Calibri"
    "Calibri Bold"
    "Calibri Light"
    "Cambria"
    "Consolas"
    "Courier New"
    "Courier New Bold"
    "Georgia"
    "Impact"
    "Microsoft Sans Serif"
    "Palatino Linotype"
    "Segoe UI"
    "Segoe UI Bold"
    "Tahoma"
    "Tahoma Bold"
    "Times New Roman"
    "Times New Roman Bold"
    "Trebuchet MS"
    "Trebuchet MS Bold"
    "Verdana"
    "Verdana Bold"
  )
)


;;; --- ACI-Farbliste fuer Block (ohne "Von Block") ---
;;; Rueckgabe: Assoziationsliste ((label . aci-code) ...)
(defun SBZ:get-block-color-list ( / )
  (list
    '("1 - Rot" . 1)
    '("2 - Gelb" . 2)
    '("3 - Gruen" . 3)
    '("4 - Cyan" . 4)
    '("5 - Blau" . 5)
    '("6 - Magenta" . 6)
    '("7 - Weiss" . 7)
    '("256 - VonLayer" . 256)
  )
)

;;; --- ACI-Farbliste fuer Attribute (mit "Von Block" am Anfang) ---
(defun SBZ:get-attr-color-list ( / )
  (list
    '("Von Block" . 0)
    '("1 - Rot" . 1)
    '("2 - Gelb" . 2)
    '("3 - Gruen" . 3)
    '("4 - Cyan" . 4)
    '("5 - Blau" . 5)
    '("6 - Magenta" . 6)
    '("7 - Weiss" . 7)
    '("256 - VonLayer" . 256)
  )
)

;;; --- ACI-Code → Index in Farbliste finden ---
(defun SBZ:color-to-index (aci-code color-list / idx i)
  (setq idx 0 i 0)
  (foreach item color-list
    (if (= (cdr item) aci-code) (setq idx i))
    (setq i (1+ i))
  )
  idx
)


;;; --- DCL schreiben (Embedded, Temp-Datei) ---
;;; --- DCL schreiben (Embedded, Temp-Datei) ---
;;; Layout: 4 Boxen (Zeichnung, Modus, Block, Attribut) + 3 Buttons
(defun SBZ:write-settings-dcl ( / dcl-file fp)
  (setq dcl-file (vl-filename-mktemp "sbz_set" nil ".dcl"))
  (setq fp (open dcl-file "w"))
  (write-line "sbz_settings : dialog {" fp)
  (write-line "  label = \"SetBlockZ - Einstellungen\";" fp)
  (write-line "  width = 55;" fp)
  (write-line "  spacer;" fp)

  ;; ===== GRUPPE (oben) =====
  (write-line "  : row {" fp)
  (write-line "    : popup_list { key = \"group\"; label = \"Gruppe:\"; }" fp)
  (write-line "    : button { key = \"groupdel\"; label = \"Loeschen\"; width = 8; fixed_width = true; }" fp)
  (write-line "  }" fp)
  ;; Info-Zeile + Buttons direkt unter Gruppe
  (write-line "  : text { key = \"groupinfo\"; label = \"\"; }" fp)
  (write-line "  : row {" fp)
  (write-line "    : button { key = \"grp_add\"; label = \"Hinzufuegen\"; width = 16; fixed_width = true; }" fp)
  (write-line "    : button { key = \"grp_remove\"; label = \"Entfernen\"; width = 16; fixed_width = true; }" fp)
  (write-line "  }" fp)
  (write-line "  spacer;" fp)

  ;; ===== IMPORT =====
  (write-line "  : boxed_column {" fp)
  (write-line "    label = \"Import\";" fp)
  (write-line "    : row {" fp)
  (write-line "      : button { key = \"import\"; label = \"Leica Punkte importieren...\"; width = 30; fixed_width = true; }" fp)
  (write-line "    }" fp)
  (write-line "  }" fp)
  (write-line "  spacer;" fp)

  ;; ===== BOX 1: ZEICHNUNG =====
  (write-line "  : boxed_column {" fp)
  (write-line "    label = \"Zeichnung\";" fp)
  (write-line "    : edit_box { key = \"bau0\"; label = \"DWG Bau-0 (m):  \"; edit_width = 12; }" fp)
  (write-line "    : row {" fp)
  (write-line "      : edit_box { key = \"groupbau0\"; label = \"Gruppen Bau-0:\"; edit_width = 12; }" fp)
  (write-line "      : toggle { key = \"usegroupbau0\"; label = \"Eigener\"; }" fp)
  (write-line "    }" fp)
  (write-line "  }" fp)
  (write-line "  spacer;" fp)

  ;; ===== BOX 2: MODUS =====
  (write-line "  : boxed_column {" fp)
  (write-line "    label = \"Modus\";" fp)
  (write-line "    : toggle { key = \"copymode\"; label = \"Kopie-Block einfuegen (Original unveraendert)\"; }" fp)
  (write-line "  }" fp)
  (write-line "  spacer;" fp)

  ;; ===== BOX 3: BLOCK =====
  ;; concatenation mit 2 gleich breiten columns
  ;; Labels gepadded: links 7 Zeichen, rechts 12 Zeichen
  (write-line "  : boxed_column {" fp)
  (write-line "    label = \"Block\";" fp)
  (write-line "    : concatenation {" fp)
  (write-line "      : column { fixed_width = true; width = 23;" fp)
  (write-line "        : edit_box { key = \"copyblock\"; label = \"Name:  \"; }" fp)
  (write-line "        : popup_list { key = \"colorblock\"; label = \"Farbe: \"; }" fp)
  (write-line "      }" fp)
  (write-line "      : column { fixed_width = true; width = 23;" fp)
  (write-line "        : edit_box { key = \"copylayer\"; label = \"Layer:      \"; }" fp)
  (write-line "        : edit_box { key = \"scale\"; label = \"Skalierung:\"; }" fp)
  (write-line "      }" fp)
  (write-line "    }" fp)
  (write-line "  }" fp)
  (write-line "  spacer;" fp)

  ;; ===== BOX 4: ATTRIBUT =====
  ;; Schriftart oben, dann 4-Spalten Tabelle mit concatenation
  (write-line "  : boxed_column {" fp)
  (write-line "    label = \"Attribut\";" fp)
  (write-line "    : popup_list { key = \"font\"; label = \"Schriftart:\"; }" fp)
  (write-line "    spacer;" fp)
  ;; concatenation: 4 Spalten vertikal ausgerichtet
  (write-line "    : concatenation {" fp)
  ;; Spalte 1: Labels
  (write-line "      : column { fixed_width = true; width = 8;" fp)
  (write-line "        : text { value = \"\"; }" fp)
  (write-line "        : text { value = \"Absolut\"; }" fp)
  (write-line "        : text { value = \"Relativ\"; }" fp)
  (write-line "        : text { value = \"Bau-0\"; }" fp)
  (write-line "      }" fp)
  ;; Spalte 2: Farbe
  (write-line "      : column { fixed_width = true; width = 16;" fp)
  (write-line "        : text { value = \"Farbe\"; }" fp)
  (write-line "        : popup_list { key = \"colorabs\"; }" fp)
  (write-line "        : popup_list { key = \"colorrel\"; }" fp)
  (write-line "        : popup_list { key = \"colorbau0\"; }" fp)
  (write-line "      }" fp)
  ;; Spalte 3: Frieren
  (write-line "      : column { fixed_width = true; width = 6;" fp)
  (write-line "        : text { value = \"Frieren\"; }" fp)
  (write-line "        : toggle { key = \"freezeabs\"; label = \"\"; }" fp)
  (write-line "        : toggle { key = \"freezerel\"; label = \"\"; }" fp)
  (write-line "        : toggle { key = \"freezebau0\"; label = \"\"; }" fp)
  (write-line "      }" fp)
  ;; Spalte 4: Suffix (nur Absolut hat edit_box, Rest = popup_list als Platzhalter)
  (write-line "      : column { fixed_width = true; width = 14;" fp)
  (write-line "        : text { value = \"Suffix\"; }" fp)
  (write-line "        : edit_box { key = \"suffix\"; label = \"\"; edit_width = 8; }" fp)
  (write-line "        : popup_list { key = \"dummy1\"; label = \"\"; }" fp)
  (write-line "        : popup_list { key = \"dummy2\"; label = \"\"; }" fp)
  (write-line "      }" fp)
  (write-line "    }" fp)
  (write-line "  }" fp)
  (write-line "  spacer;" fp)

  ;; ===== BUTTONS: Standard | Aendern | Speichern | Schliessen =====
  (write-line "  : row {" fp)
  (write-line "    : button { key = \"defaults\"; label = \"Standard\"; width = 10; fixed_width = true; }" fp)
  (write-line "    : spacer { width = 1; }" fp)
  (write-line "    : button { key = \"update\"; label = \"Aendern\"; width = 10; fixed_width = true; }" fp)
  (write-line "    : button { key = \"save\"; label = \"Speichern\"; is_default = true; width = 10; fixed_width = true; }" fp)
  (write-line "    : button { key = \"close\"; label = \"Schliessen\"; is_cancel = true; width = 10; fixed_width = true; }" fp)
  (write-line "  }" fp)
  (write-line "}" fp)

  ;; ===== IMPORT SUB-DIALOG =====
  (write-line "" fp)
  (write-line "sbz_import : dialog {" fp)
  (write-line "  label = \"Leica Punkte importieren\";" fp)
  (write-line "  width = 50;" fp)
  (write-line "  spacer;" fp)
  ;; Datei
  (write-line "  : row {" fp)
  (write-line "    : edit_box { key = \"imp_file\"; label = \"Datei:\"; edit_width = 30; }" fp)
  (write-line "    : button { key = \"imp_browse\"; label = \"...\"; width = 4; fixed_width = true; }" fp)
  (write-line "  }" fp)
  ;; Vorschau
  (write-line "  : text { key = \"imp_preview\"; label = \"\"; }" fp)
  (write-line "  spacer;" fp)
  ;; Format
  (write-line "  : boxed_column {" fp)
  (write-line "    label = \"Format\";" fp)
  (write-line "    : row {" fp)
  (write-line "      : popup_list { key = \"imp_order\"; label = \"Reihenfolge:\"; width = 20; }" fp)
  (write-line "      : popup_list { key = \"imp_sep\"; label = \"Trennzeichen:\"; width = 20; }" fp)
  (write-line "    }" fp)
  (write-line "  }" fp)
  (write-line "  spacer;" fp)
  ;; Hoehen-Einstellungen
  (write-line "  : boxed_column {" fp)
  (write-line "    label = \"Hoehen\";" fp)
  (write-line "    : row {" fp)
  (write-line "      : edit_box { key = \"imp_bau0\"; label = \"Bau-0 (m):\"; edit_width = 12; }" fp)
  (write-line "      : popup_list { key = \"imp_zmode\"; label = \"Gemessen als:\"; width = 20; }" fp)
  (write-line "    }" fp)
  (write-line "  }" fp)
  (write-line "  spacer;" fp)
  ;; Optionen
  (write-line "  : boxed_column {" fp)
  (write-line "    label = \"Optionen\";" fp)
  (write-line "    : toggle { key = \"imp_layercol\"; label = \"Layer aus Spalte uebernehmen (letzte Spalte)\"; }" fp)
  (write-line "    : toggle { key = \"imp_group\"; label = \"Pro Layer eine Gruppe erstellen\"; }" fp)
  (write-line "  }" fp)
  (write-line "  spacer;" fp)
  ;; Buttons
  (write-line "  : row {" fp)
  (write-line "    : button { key = \"imp_ok\"; label = \"Importieren\"; is_default = true; width = 12; fixed_width = true; }" fp)
  (write-line "    : button { key = \"imp_cancel\"; label = \"Abbrechen\"; is_cancel = true; width = 12; fixed_width = true; }" fp)
  (write-line "  }" fp)
  (write-line "}" fp)
  (close fp)
  dcl-file
)


;;; --- Kopie-Modus Felder enabled/disabled je nach Toggle ---
(defun SBZ:settings-update-copyblock-state (toggle-val / mode)
  (setq mode (if (= toggle-val "1") 0 1))
  (mode_tile "copyblock" mode)
  (mode_tile "copylayer" mode)
  (mode_tile "scale" mode)
  (mode_tile "suffix" mode)
  (mode_tile "colorblock" mode)
  (mode_tile "font" mode)
  (mode_tile "colorabs" mode)
  (mode_tile "colorrel" mode)
  (mode_tile "colorbau0" mode)
  (mode_tile "freezeabs" mode)
  (mode_tile "freezerel" mode)
  (mode_tile "freezebau0" mode)
  (mode_tile "update" mode)
)


;;; --- Standard-Werte in Dialog-Felder zuruecksetzen (Dialog bleibt offen) ---
;;; Wird vom "Standard" Button aufgerufen
;;; Benoetigt font-names, block-colors, attr-colors als globale Variablen im Dialog-Scope
(defun SBZ:reset-defaults ( / idx)
  ;; Zeichnung (Gruppen-Bau0 zuruecksetzen, DWG Bau-0 bleibt)
  (set_tile "bau0" "0.000")
  (set_tile "groupbau0" "")
  (set_tile "usegroupbau0" "0")
  (mode_tile "groupbau0" 1)
  ;; Gruppe: BLEIBT gewaehlt (User will Gruppe auf Standard setzen)
  ;; Modus
  (set_tile "copymode" "1")
  ;; Block
  (set_tile "copyblock" "VM_Hoehe")
  (set_tile "copylayer" "HP")
  (set_tile "suffix" "m ü. A.")
  (set_tile "scale" "1.0000")
  ;; Block-Farbe: 7 = Weiss
  (setq idx (SBZ:color-to-index 7 block-colors))
  (set_tile "colorblock" (itoa idx))
  ;; Schriftart: Arial
  (setq idx (vl-position "Arial" font-names))
  (if (not idx) (setq idx 0))
  (set_tile "font" (itoa idx))
  ;; Attribut-Farben: Von Block (0)
  (setq idx (SBZ:color-to-index 0 attr-colors))
  (set_tile "colorabs" (itoa idx))
  (set_tile "colorrel" (itoa idx))
  (set_tile "colorbau0" (itoa idx))
  ;; Freeze
  (set_tile "freezeabs" "0")
  (set_tile "freezerel" "0")
  (set_tile "freezebau0" "1")
  ;; Felder aktivieren (Kopie-Modus = ein)
  (SBZ:settings-update-copyblock-state "1")
)


;;; --- Gruppen-Settings in Dialog-Felder laden ---
;;; Wird aufgerufen wenn User eine Gruppe im Dropdown waehlt
;;; Benoetigt font-names, block-colors, attr-colors im Dialog-Scope
(defun SBZ:load-group-to-dialog (group-name / gdata val idx)
  (setq gdata (SBZ:load-group group-name))
  (if gdata
    (progn
      ;; Bau-0: Gruppen-eigener oder DWG-Standard
      (setq val (cdr (assoc "BAU0" gdata)))
      (if (and val (/= val ""))
        (progn
          (set_tile "groupbau0" val)
          (set_tile "usegroupbau0" "1")
          (mode_tile "groupbau0" 0)
        )
        (progn
          (set_tile "groupbau0" "")
          (set_tile "usegroupbau0" "0")
          (mode_tile "groupbau0" 1)
        )
      )
      ;; Block-Settings
      (if (setq val (cdr (assoc "COPYLAYER" gdata)))
        (set_tile "copylayer" val))
      (if (setq val (cdr (assoc "SCALE" gdata)))
        (set_tile "scale" val))
      (if (setq val (cdr (assoc "SUFFIX" gdata)))
        (set_tile "suffix" val))
      ;; Block-Farbe
      (if (setq val (cdr (assoc "COLORBLOCK" gdata)))
        (set_tile "colorblock" (itoa (SBZ:color-to-index (atoi val) block-colors))))
      ;; Schriftart
      (if (setq val (cdr (assoc "FONT" gdata)))
        (progn
          (setq idx (vl-position (strcase val) (mapcar 'strcase font-names)))
          (if idx (set_tile "font" (itoa idx)))
        )
      )
      ;; Attribut-Farben
      (if (setq val (cdr (assoc "COLORABS" gdata)))
        (set_tile "colorabs" (itoa (SBZ:color-to-index (atoi val) attr-colors))))
      (if (setq val (cdr (assoc "COLORREL" gdata)))
        (set_tile "colorrel" (itoa (SBZ:color-to-index (atoi val) attr-colors))))
      (if (setq val (cdr (assoc "COLORBAU0" gdata)))
        (set_tile "colorbau0" (itoa (SBZ:color-to-index (atoi val) attr-colors))))
      ;; Freeze
      (if (setq val (cdr (assoc "FREEZEABS" gdata)))
        (set_tile "freezeabs" val))
      (if (setq val (cdr (assoc "FREEZEREL" gdata)))
        (set_tile "freezerel" val))
      (if (setq val (cdr (assoc "FREEZEBAU0" gdata)))
        (set_tile "freezebau0" val))
      ;; Kopie-Modus immer ein bei Gruppen
      (set_tile "copymode" "1")
      (SBZ:settings-update-copyblock-state "1")
      ;; Info-Zeile aktualisieren + Buttons aktivieren
      (SBZ:update-groupinfo group-name)
      (mode_tile "grp_add" 0)
      (mode_tile "grp_remove" 0)
      (SBZ:log-write "INFO" (strcat "Gruppe '" group-name "' in Dialog geladen"))
    )
  )
)


;;; ----------------------------------------------------------------------------
;;; SBZ:update-groupinfo
;;; Aktualisiert die Info-Zeile im Dialog mit Anzahl Bloecke in Gruppe
;;; Parameter: group-name - Gruppenname oder nil
;;; ----------------------------------------------------------------------------
(defun SBZ:update-groupinfo (group-name / ents count)
  (if (and group-name (/= group-name ""))
    (progn
      (setq ents (SBZ:get-group-entities group-name))
      (setq count (if ents (length ents) 0))
      (set_tile "groupinfo"
        (strcat (itoa count) " Bloecke in Gruppe '" group-name "'"))
    )
    (set_tile "groupinfo" "")
  )
)


;;; ----------------------------------------------------------------------------
;;; SBZ:dlg-grp-add
;;; Hinzufuegen-Button: Dialog verstecken, User waehlt Quell-Bloecke,
;;; Kopie-Bloecke werden erstellt + XData gesetzt, Dialog zeigen
;;; Benoetigt Zugriff auf: sel-group, sel-group-data, bau0
;;; ----------------------------------------------------------------------------
(defun SBZ:dlg-grp-add ( / dlg-idx)
  ;; sel-group aus aktuellem Dropdown lesen
  (setq dlg-idx (atoi (get_tile "group")))
  (if (and (> dlg-idx 0) group-names)
    (progn
      (setq sel-group (nth (1- dlg-idx) group-names))
      (setq sel-group-data (SBZ:load-group sel-group))
      (done_dialog 10)
    )
    (alert "Zuerst eine Gruppe waehlen.")
  )
)


;;; ----------------------------------------------------------------------------
;;; SBZ:dlg-grp-remove
;;; Entfernen-Button: Dialog verstecken, User waehlt Kopie-Bloecke,
;;; ausgewaehlte werden geloescht, Dialog zeigen
;;; ----------------------------------------------------------------------------
(defun SBZ:dlg-grp-remove ( / dlg-idx)
  ;; sel-group aus aktuellem Dropdown lesen
  (setq dlg-idx (atoi (get_tile "group")))
  (if (and (> dlg-idx 0) group-names)
    (progn
      (setq sel-group (nth (1- dlg-idx) group-names))
      (done_dialog 11)
    )
    (alert "Zuerst eine Gruppe waehlen.")
  )
)


;;; ============================================================================
;;; LEICA IMPORT FUNKTIONEN
;;; ============================================================================

;;; ----------------------------------------------------------------------------
;;; SBZ:write-import-dcl
;;; Schreibt die DCL-Datei fuer den Import-Dialog
;;; Rueckgabe: DCL-Dateipfad
;;; ----------------------------------------------------------------------------
(defun SBZ:write-import-dcl ( / dcl-file fp)
  (setq dcl-file (vl-filename-mktemp "sbz_imp" nil ".dcl"))
  (setq fp (open dcl-file "w"))
  (write-line "sbz_import : dialog {" fp)
  (write-line "  label = \"SetBlockZ - Leica Import\";" fp)
  (write-line "  width = 55;" fp)
  (write-line "  spacer;" fp)
  ;; Datei
  (write-line "  : row {" fp)
  (write-line "    : edit_box { key = \"filepath\"; label = \"Datei:\"; width = 40; }" fp)
  (write-line "    : button { key = \"browse\"; label = \"...\"; width = 4; fixed_width = true; }" fp)
  (write-line "  }" fp)
  (write-line "  spacer;" fp)
  ;; Format
  (write-line "  : boxed_column {" fp)
  (write-line "    label = \"Format\";" fp)
  (write-line "    : row {" fp)
  (write-line "      : popup_list { key = \"coordorder\"; label = \"Reihenfolge:\"; width = 16; }" fp)
  (write-line "      : popup_list { key = \"separator\"; label = \"Trennzeichen:\"; width = 16; }" fp)
  (write-line "    }" fp)
  (write-line "    : text { key = \"preview\"; label = \"\"; }" fp)
  (write-line "  }" fp)
  (write-line "  spacer;" fp)
  ;; Hoehen-Einstellungen
  (write-line "  : boxed_column {" fp)
  (write-line "    label = \"Hoehen\";" fp)
  (write-line "    : row {" fp)
  (write-line "      : popup_list { key = \"zmode\"; label = \"Gemessen als:\"; width = 16; }" fp)
  (write-line "      : edit_box { key = \"imp_bau0\"; label = \"Bau-0 (m):\"; edit_width = 12; }" fp)
  (write-line "    }" fp)
  (write-line "    : popup_list { key = \"ztarget\"; label = \"Z-Koordinate nach:\"; width = 16; }" fp)
  (write-line "  }" fp)
  (write-line "  spacer;" fp)
  ;; Buttons
  (write-line "  : row {" fp)
  (write-line "    : button { key = \"accept\"; label = \"Importieren\"; is_default = true; width = 16; fixed_width = true; }" fp)
  (write-line "    : button { key = \"cancel\"; label = \"Abbrechen\"; is_cancel = true; width = 16; fixed_width = true; }" fp)
  (write-line "  }" fp)
  (write-line "}" fp)
  (close fp)
  dcl-file
)


;;; ----------------------------------------------------------------------------
;;; SBZ:detect-separator
;;; Erkennt das Trennzeichen einer Leica-Exportdatei
;;; Parameter: line - Erste Zeile der Datei (String)
;;; Rueckgabe: Index fuer Popup (0=Komma, 1=Semikolon, 2=Tab, 3=Leerzeichen)
;;; ----------------------------------------------------------------------------
(defun SBZ:detect-separator (line / )
  (cond
    ((vl-string-search ";" line)  1)    ;; Semikolon
    ((vl-string-search "\t" line) 2)    ;; Tab
    ((vl-string-search "," line)  0)    ;; Komma
    (T 3)                                ;; Leerzeichen
  )
)


;;; ----------------------------------------------------------------------------
;;; SBZ:split-string
;;; Teilt einen String anhand eines Trennzeichens
;;; Parameter: str - String, delim - Trennzeichen (String, 1 Zeichen)
;;; Rueckgabe: Liste von Strings
;;; ----------------------------------------------------------------------------
(defun SBZ:split-string (str delim / pos result part)
  (setq result nil)
  (while (setq pos (vl-string-search delim str))
    (setq part (substr str 1 pos))
    (setq result (cons part result))
    (setq str (substr str (+ pos 2)))
  )
  (setq result (cons str result))
  (reverse result)
)


;;; ----------------------------------------------------------------------------
;;; SBZ:parse-leica-file
;;; Liest eine Leica-Exportdatei und gibt eine Liste von Punkt-Daten zurueck
;;; Parameter:
;;;   filepath   - Pfad zur Datei (String)
;;;   sep        - Trennzeichen (String: "," ";" "\t" " ")
;;;   coord-order - "ONH" oder "NOH"
;;; Rueckgabe: Liste von (name east north height layer) oder nil
;;; ----------------------------------------------------------------------------
(defun SBZ:parse-leica-file (filepath sep coord-order / fp line parts
                              name c1 c2 c3 layer east north height
                              points count-ok count-err)
  (setq fp (open filepath "r"))
  (if (not fp)
    (progn
      (SBZ:log-write "ERROR" (strcat "Datei nicht geoeffnet: " filepath))
      nil
    )
    (progn
      (setq points nil count-ok 0 count-err 0)
      (while (setq line (read-line fp))
        ;; CR/LF entfernen
        (setq line (vl-string-trim "\r\n " line))
        (if (and line (/= line ""))
          (progn
            (setq parts (SBZ:split-string line sep))
            ;; Mindestens 4 Spalten: Name, Coord1, Coord2, Coord3
            (if (>= (length parts) 4)
              (progn
                (setq name (nth 0 parts))
                (setq c1 (atof (nth 1 parts)))
                (setq c2 (atof (nth 2 parts)))
                (setq c3 (atof (nth 3 parts)))
                ;; Layer (optional, Spalte 5)
                (setq layer (if (>= (length parts) 5) (nth 4 parts) "0"))
                ;; CR/LF aus Layer entfernen
                (setq layer (vl-string-trim "\r\n " layer))
                ;; Koordinaten-Reihenfolge
                (if (= coord-order "ONH")
                  (progn (setq east c1) (setq north c2) (setq height c3))
                  (progn (setq north c1) (setq east c2) (setq height c3))
                )
                (setq points (cons (list name east north height layer) points))
                (setq count-ok (1+ count-ok))
              )
              (setq count-err (1+ count-err))
            )
          )
        )
      )
      (close fp)
      (SBZ:log-write "INFO"
        (strcat "Import: " (itoa count-ok) " Punkte gelesen, "
                (itoa count-err) " Fehler"))
      (reverse points)
    )
  )
)


;;; ----------------------------------------------------------------------------
;;; SBZ:import-create-blocks
;;; Erstellt Kopie-Bloecke aus importierten Punktdaten
;;; Parameter:
;;;   points   - Liste von (name east north height layer)
;;;   bau0     - Bau-0-Hoehe (Real)
;;;   z-mode   - "ABS" oder "REL"
;;; Rueckgabe: Anzahl erstellter Bloecke
;;; ----------------------------------------------------------------------------
(defun SBZ:import-create-blocks (points bau0 z-mode z-target / pt name east north height
                                  layer abs-h rel-z ins-z group-name
                                  copy-blk-name ins-pt new-ent
                                  scale suffix style-name copy-layer
                                  abs-str rel-str bau0-str tag-str
                                  att-ent att-data attrs bks-angle
                                  count layers-created)
  (setq count 0)
  (setq layers-created nil)
  (setq scale (SBZ:get-scale))
  (setq suffix (SBZ:get-suffix))
  (setq style-name (SBZ:ensure-textstyle (SBZ:get-font)))
  ;; BKS-Rotation
  (setq bks-angle (angle '(0.0 0.0 0.0) (getvar "UCSXDIR")))
  ;; Bau-0 String fuer Gruppe
  (setq bau0-str
    (if (equal bau0 (SBZ:get-bau0) 0.001) "" (rtos bau0 2 3)))

  (foreach pt points
    (setq name   (nth 0 pt))
    (setq east   (nth 1 pt))
    (setq north  (nth 2 pt))
    (setq height (nth 3 pt))
    (setq layer  (nth 4 pt))

    ;; Hoehen berechnen je nach "Gemessen als" (z-mode)
    (if (= z-mode "ABS")
      (progn
        (setq abs-h height)
        (setq rel-z (- height bau0))
      )
      (progn
        ;; Relativ gemessen: height = relative Hoehe
        (setq rel-z height)
        (setq abs-h (+ bau0 height))
      )
    )
    ;; Z-Koordinate des Blocks je nach "Z-Koordinate nach" (z-target)
    (setq ins-z (if (= z-target "ABS") abs-h rel-z))

    ;; Gruppenname = Layername aus Datei
    (setq group-name layer)
    (setq copy-blk-name (SBZ:build-copyblock-name group-name))

    ;; Block-Definition sicherstellen (einmal pro Layer)
    (if (not (member group-name layers-created))
      (progn
        (SBZ:ensure-copyblock-def copy-blk-name)
        (setq layers-created (cons group-name layers-created))
        ;; Gruppe als XRecord speichern (falls nicht vorhanden)
        (if (not (SBZ:load-group group-name))
          (SBZ:save-group group-name
            (SBZ:group-data-from-current
              "IMPORT" "HOEHE" bau0-str z-mode group-name))
        )
      )
    )

    ;; Layer + Sublayer erstellen
    (setq copy-layer (SBZ:get-copy-layername z-mode bau0 group-name))
    (SBZ:ensure-attr-layers copy-layer)

    ;; Insert-Punkt (X=Ost, Y=Nord, Z=Hoehe)
    (setq ins-pt (list east north ins-z))

    ;; Block einfuegen
    (setq new-ent
      (vl-catch-all-apply
        '(lambda ()
          (vla-InsertBlock
            (vla-get-modelspace (vla-get-activedocument (vlax-get-acad-object)))
            (vlax-3d-point ins-pt)
            copy-blk-name
            scale scale scale
            bks-angle
          )
        )
      )
    )
    (if (and new-ent (not (vl-catch-all-error-p new-ent)))
      (progn
        ;; Attribute setzen
        (setq abs-str (strcat (SBZ:rtos-fixed abs-h 2)
                              (if (and suffix (/= suffix ""))
                                (strcat " " suffix) "")))
        (cond
          ((> rel-z 0.001)  (setq rel-str (strcat "+" (SBZ:rtos-fixed rel-z 2))))
          ((< rel-z -0.001) (setq rel-str (SBZ:rtos-fixed rel-z 2)))
          (T (setq rel-str (strcat "%%P" (SBZ:rtos-fixed rel-z 2))))
        )
        (setq bau0-str-txt (strcat "%%P0.00 = " (SBZ:rtos-fixed bau0 2)
                                    (if (and suffix (/= suffix ""))
                                      (strcat " " suffix) "")))
        (setq attrs (vlax-invoke new-ent 'GetAttributes))
        (foreach attr attrs
          (setq tag-str (strcase (vla-get-TagString attr)))
          (setq att-ent (vlax-vla-object->ename attr))
          (setq att-data (entget att-ent))
          (cond
            ((= tag-str "HOEHE_ABS")
              (setq att-data (subst (cons 1 abs-str) (assoc 1 att-data) att-data))
              (setq att-data (subst (cons 70 16) (assoc 70 att-data) att-data))
              (setq att-data (subst (cons 7 style-name) (assoc 7 att-data) att-data))
              (setq att-data (subst (cons 8 (strcat copy-layer "-AttABS"))
                                    (assoc 8 att-data) att-data))
              (if (/= *SBZ:cfg-color-abs* 0)
                (setq att-data (subst (cons 62 *SBZ:cfg-color-abs*) (assoc 62 att-data) att-data)))
              (entmod att-data) (entupd att-ent)
            )
            ((= tag-str "HOEHE_REL")
              (setq att-data (subst (cons 1 rel-str) (assoc 1 att-data) att-data))
              (setq att-data (subst (cons 70 16) (assoc 70 att-data) att-data))
              (setq att-data (subst (cons 7 style-name) (assoc 7 att-data) att-data))
              (setq att-data (subst (cons 8 (strcat copy-layer "-AttREL"))
                                    (assoc 8 att-data) att-data))
              (if (/= *SBZ:cfg-color-rel* 0)
                (setq att-data (subst (cons 62 *SBZ:cfg-color-rel*) (assoc 62 att-data) att-data)))
              (entmod att-data) (entupd att-ent)
            )
            ((= tag-str "HOEHE_BAU0")
              (setq att-data (subst (cons 1 bau0-str-txt) (assoc 1 att-data) att-data))
              (setq att-data (subst (cons 70 16) (assoc 70 att-data) att-data))
              (setq att-data (subst (cons 7 style-name) (assoc 7 att-data) att-data))
              (setq att-data (subst (cons 8 (strcat copy-layer "-AttBAU0"))
                                    (assoc 8 att-data) att-data))
              (if (/= *SBZ:cfg-color-bau0* 0)
                (setq att-data (subst (cons 62 *SBZ:cfg-color-bau0*) (assoc 62 att-data) att-data)))
              (entmod att-data) (entupd att-ent)
            )
          )
        )
        ;; Block auf Layer + Farbe
        (vl-catch-all-apply 'vla-put-Layer (list new-ent copy-layer))
        (vl-catch-all-apply 'vla-put-Color (list new-ent *SBZ:cfg-color-block*))
        ;; XData setzen (Gruppenname, kein Quell-Handle bei Import)
        (SBZ:set-xdata (vlax-vla-object->ename new-ent) group-name "")
        (setq count (1+ count))
      )
    )
  )
  (SBZ:log-write "INFO" (strcat "Import: " (itoa count) " Bloecke erstellt"))
  count
)


;;; ----------------------------------------------------------------------------
;;; SBZ:run-import-dialog
;;; Oeffnet den Import-Dialog, liest Einstellungen, importiert
;;; Rueckgabe: Anzahl importierter Punkte oder nil
;;; ----------------------------------------------------------------------------
(defun SBZ:run-import-dialog ( / dcl-file dcl-id result
                                  filepath sep-idx coord-idx zmode-idx ztarget-idx
                                  imp-bau0 separator coord-order z-mode z-target
                                  sep-list points count
                                  first-line preview-text)
  (setq dcl-file (SBZ:write-import-dcl))
  (setq dcl-id (load_dialog dcl-file))
  (if (not (new_dialog "sbz_import" dcl-id))
    (progn
      (SBZ:log-write "ERROR" "Import-Dialog konnte nicht geoeffnet werden")
      (unload_dialog dcl-id)
      (vl-file-delete dcl-file)
      nil
    )
    (progn
      ;; Popup-Listen befuellen
      (start_list "coordorder")
      (add_list "ONH (Ost-Nord-Hoehe)")
      (add_list "NOH (Nord-Ost-Hoehe)")
      (end_list)
      (set_tile "coordorder" "0")

      (start_list "separator")
      (add_list "Komma (,)")
      (add_list "Semikolon (;)")
      (add_list "Tab")
      (add_list "Leerzeichen")
      (end_list)
      (set_tile "separator" "0")

      (start_list "zmode")
      (add_list "Absolut (m ue. A.)")
      (add_list "Relativ (nach Bau-0)")
      (end_list)
      (set_tile "zmode" "0")

      (start_list "ztarget")
      (add_list "Absolut (Meereshoehe)")
      (add_list "Relativ (nach Bau-0)")
      (end_list)
      (set_tile "ztarget" "0")

      ;; Bau-0 aus DWG laden (0.0 als Fallback wenn nicht gesetzt)
      (setq imp-bau0 (SBZ:get-bau0))
      (if (not imp-bau0) (setq imp-bau0 0.0))
      (set_tile "imp_bau0" (rtos imp-bau0 2 3))

      ;; Datei-Browser Button
      (action_tile "browse"
        (strcat
          "(progn"
          "  (setq filepath (getfiled \"Leica Punktdatei\" \"\" \"txt;csv;asc\" 0))"
          "  (if filepath"
          "    (progn"
          "      (set_tile \"filepath\" filepath)"
          ;; Erste Zeile lesen fuer Preview + Auto-Detect
          "      (setq fp-prev (open filepath \"r\"))"
          "      (if fp-prev"
          "        (progn"
          "          (setq first-line (read-line fp-prev))"
          "          (close fp-prev)"
          "          (if first-line"
          "            (progn"
          "              (set_tile \"preview\" (strcat \"Vorschau: \" (substr first-line 1 60)))"
          "              (set_tile \"separator\" (itoa (SBZ:detect-separator first-line)))"
          "            )"
          "          )"
          "        )"
          "      )"
          "    )"
          "  )"
          ")"
        )
      )

      ;; Buttons
      (action_tile "accept"
        (strcat
          "(setq filepath (get_tile \"filepath\"))"
          "(setq sep-idx (get_tile \"separator\"))"
          "(setq coord-idx (get_tile \"coordorder\"))"
          "(setq zmode-idx (get_tile \"zmode\"))"
          "(setq ztarget-idx (get_tile \"ztarget\"))"
          "(setq imp-bau0 (get_tile \"imp_bau0\"))"
          "(done_dialog 1)"
        )
      )
      (action_tile "cancel" "(done_dialog 0)")

      (setq result (start_dialog))
      (unload_dialog dcl-id)
      (vl-file-delete dcl-file)

      (if (= result 1)
        (progn
          ;; Trennzeichen auswerten
          (setq sep-list '("," ";" "\t" " "))
          (setq separator (nth (atoi sep-idx) sep-list))
          ;; Koordinaten-Reihenfolge
          (setq coord-order (if (= coord-idx "0") "ONH" "NOH"))
          ;; Z-Modus (wie gemessen)
          (setq z-mode (if (= zmode-idx "0") "ABS" "REL"))
          ;; Z-Target (wohin Block-Z gesetzt wird)
          (setq z-target (if (= ztarget-idx "0") "ABS" "REL"))
          ;; Bau-0
          (setq imp-bau0 (atof (vl-string-subst "." "," imp-bau0)))
          ;; Datei pruefen
          (if (and filepath (/= filepath "") (findfile filepath))
            (progn
              (SBZ:log-write "INFO"
                (strcat "Import: " filepath
                        " Sep=" separator " Coord=" coord-order
                        " ZMode=" z-mode " ZTarget=" z-target
                        " Bau0=" (rtos imp-bau0 2 3)))
              ;; Datei parsen
              (setq points (SBZ:parse-leica-file filepath separator coord-order))
              (if points
                (progn
                  (princ (strcat "\n" (itoa (length points)) " Punkte gelesen. Erstelle Bloecke..."))
                  (setq count (SBZ:import-create-blocks points imp-bau0 z-mode z-target))
                  (princ (strcat "\n" (itoa count) " Bloecke importiert."))
                  count
                )
                (progn
                  (princ "\nKeine Punkte in der Datei gefunden.")
                  0
                )
              )
            )
            (progn
              (alert "Datei nicht gefunden.")
              nil
            )
          )
        )
        nil
      )
    )
  )
)


;;; ----------------------------------------------------------------------------
;;; c:SBZIMPORT - Leica Punkte importieren
;;; Eigenstaendiger Befehl fuer den Import von Vermessungspunkten
;;; ----------------------------------------------------------------------------
(defun c:SBZIMPORT ( / *error* old-cmdecho count)
  (SBZ:ensure-init)
  (defun *error* (msg)
    (if (not (SBZ:cancel-p msg))
      (progn
        (princ (strcat "\nFehler: " msg))
        (SBZ:log-write "ERROR" (strcat "SBZIMPORT Error: " msg))
      )
    )
    (if old-cmdecho (setvar "CMDECHO" old-cmdecho))
    (princ)
  )
  (setq old-cmdecho (getvar "CMDECHO"))
  (setvar "CMDECHO" 0)
  (SBZ:log-write "INFO" "Befehl SBZIMPORT gestartet")

  (setq count (SBZ:run-import-dialog))
  (if (and count (> count 0))
    (princ (strcat "\nImport abgeschlossen: " (itoa count) " Punkte."))
    (princ "\nImport abgebrochen oder keine Punkte.")
  )

  (setvar "CMDECHO" old-cmdecho)
  (SBZ:log-write "INFO" "Befehl SBZIMPORT beendet")
  (princ)
)


;;; ----------------------------------------------------------------------------
;;; SBZ:update-group-visual
;;; Aktualisiert Farbe, Layer, Schriftart, Freeze auf bestehenden Kopie-Bloecken
;;; einer Gruppe OHNE sie zu loeschen. Fuer Import-Gruppen (kein Quell-Block).
;;; Parameter:
;;;   group-name - Gruppenname (String)
;;; Rueckgabe: Anzahl aktualisierter Bloecke
;;; ----------------------------------------------------------------------------
(defun SBZ:update-group-visual (group-name / grp-ents ent ent-data
                                 copy-blk-name copy-layer style-name
                                 attrs attr tag-str att-ent att-data
                                 count)
  (setq grp-ents (SBZ:get-group-entities group-name))
  (if (not grp-ents)
    (progn
      (SBZ:log-write "WARN" (strcat "Keine Entities fuer Gruppe '" group-name "'"))
      0
    )
    (progn
      (setq count 0)
      (setq copy-blk-name (SBZ:build-copyblock-name group-name))
      (setq copy-layer (SBZ:get-copy-layername "" 0.0 group-name))
      (setq style-name (SBZ:ensure-textstyle (SBZ:get-font)))
      ;; Layer + Sub-Layer sicherstellen
      (SBZ:ensure-attr-layers copy-layer)
      ;; Block-Definition neu erstellen (mit aktuellen Einstellungen)
      (SBZ:ensure-copyblock-def copy-blk-name)
      (foreach ent grp-ents
        ;; Block-Entity: Layer + Farbe
        (setq ent-data (entget ent))
        (if (= (cdr (assoc 0 ent-data)) "INSERT")
          (progn
            ;; Block auf neuen Layer verschieben
            (setq ent-data (subst (cons 8 copy-layer) (assoc 8 ent-data) ent-data))
            ;; Block-Farbe setzen
            (if (assoc 62 ent-data)
              (setq ent-data (subst (cons 62 *SBZ:cfg-color-block*) (assoc 62 ent-data) ent-data))
              (setq ent-data (append ent-data (list (cons 62 *SBZ:cfg-color-block*))))
            )
            (entmod ent-data)
            ;; Attribute aktualisieren: Layer, Farbe, Schriftart
            (setq attrs (vlax-invoke (vlax-ename->vla-object ent) 'GetAttributes))
            (foreach attr attrs
              (setq tag-str (strcase (vla-get-TagString attr)))
              (setq att-ent (vlax-vla-object->ename attr))
              (setq att-data (entget att-ent))
              (cond
                ((= tag-str "HOEHE_ABS")
                  (setq att-data (subst (cons 8 (strcat copy-layer "-AttABS"))
                                        (assoc 8 att-data) att-data))
                  (setq att-data (subst (cons 7 style-name) (assoc 7 att-data) att-data))
                  (if (/= *SBZ:cfg-color-abs* 0)
                    (if (assoc 62 att-data)
                      (setq att-data (subst (cons 62 *SBZ:cfg-color-abs*) (assoc 62 att-data) att-data))
                      (setq att-data (append att-data (list (cons 62 *SBZ:cfg-color-abs*))))
                    )
                  )
                  (entmod att-data) (entupd att-ent)
                )
                ((= tag-str "HOEHE_REL")
                  (setq att-data (subst (cons 8 (strcat copy-layer "-AttREL"))
                                        (assoc 8 att-data) att-data))
                  (setq att-data (subst (cons 7 style-name) (assoc 7 att-data) att-data))
                  (if (/= *SBZ:cfg-color-rel* 0)
                    (if (assoc 62 att-data)
                      (setq att-data (subst (cons 62 *SBZ:cfg-color-rel*) (assoc 62 att-data) att-data))
                      (setq att-data (append att-data (list (cons 62 *SBZ:cfg-color-rel*))))
                    )
                  )
                  (entmod att-data) (entupd att-ent)
                )
                ((= tag-str "HOEHE_BAU0")
                  (setq att-data (subst (cons 8 (strcat copy-layer "-AttBAU0"))
                                        (assoc 8 att-data) att-data))
                  (setq att-data (subst (cons 7 style-name) (assoc 7 att-data) att-data))
                  (if (/= *SBZ:cfg-color-bau0* 0)
                    (if (assoc 62 att-data)
                      (setq att-data (subst (cons 62 *SBZ:cfg-color-bau0*) (assoc 62 att-data) att-data))
                      (setq att-data (append att-data (list (cons 62 *SBZ:cfg-color-bau0*))))
                    )
                  )
                  (entmod att-data) (entupd att-ent)
                )
              )
            )
            (entupd ent)
            (setq count (1+ count))
          )
        )
      )
      (SBZ:log-write "INFO"
        (strcat "Gruppe '" group-name "': " (itoa count) " Bloecke visuell aktualisiert"))
      count
    )
  )
)


;;; --- Hauptfunktion SBZSETTINGS ---
(defun c:SBZSETTINGS ( / *error* dcl-file dcl-id
                         bau0 scale suffix
                         font-names font-idx
                         block-colors attr-colors
                         last-blk last-attr
                         dlg-bau0
                         dlg-copymode dlg-copyblock dlg-scale dlg-suffix
                         dlg-copylayer dlg-font
                         dlg-colorblock dlg-colorabs dlg-colorrel dlg-colorbau0
                         dlg-freezeabs dlg-freezerel dlg-freezebau0
                         dlg-action dlg-group dlg-groupbau0 dlg-usegroupbau0
                         result count ss ss-work blocks blk-def old-copyblock
                         group-names sel-group sel-group-data bau0-str
                         ss-add ss-filtered ss-remove ent ent-data i
                         add-count rem-count copy-blk-name)
  (SBZ:ensure-init)
  (defun *error* (msg)
    (if (not (SBZ:cancel-p msg))
      (progn
        (princ (strcat "\nFehler: " msg))
        (SBZ:log-write "ERROR" (strcat "SBZSETTINGS Error-Handler: " msg))
      )
    )
    (if (and dcl-id (< 0 dcl-id)) (unload_dialog dcl-id))
    (if (and dcl-file (findfile dcl-file)) (vl-file-delete dcl-file))
    (princ)
  )

  (SBZ:log-write "INFO" "Befehl SBZSETTINGS gestartet")

  ;; Werte lesen
  (setq bau0 (SBZ:get-bau0))
  (if (not bau0) (setq bau0 0.0))
  (setq last-blk (SBZ:get-last-blockname))
  (setq last-attr (SBZ:get-last-attrtag))
  (setq font-names (SBZ:get-font-list))
  (setq block-colors (SBZ:get-block-color-list))
  (setq attr-colors (SBZ:get-attr-color-list))
  ;; Gruppennamen aus DWG laden
  (setq group-names (SBZ:get-group-names))
  (if (not group-names) (setq group-names nil))

  ;; DCL schreiben und laden
  (setq dcl-file (SBZ:write-settings-dcl))
  (setq dcl-id (load_dialog dcl-file))

  (if (not dcl-id)
    (progn
      (princ "\nFehler: Settings-DCL konnte nicht geladen werden.")
      (SBZ:log-write "ERROR" "Settings-DCL load fehlgeschlagen")
      (vl-file-delete dcl-file)
      (princ)
    )
    (progn
      ;; Dialog-Schleife: wird bei Hinzufuegen/Entfernen wiederholt
      (setq *SBZ:dlg-running* T)
      (while *SBZ:dlg-running*
      ;; dlg-action zuruecksetzen fuer diesen Durchlauf
      (setq dlg-action nil)
      ;; === DIALOG OEFFNEN ===
      (if (not (new_dialog "sbz_settings" dcl-id))
        (progn
          (SBZ:log-write "ERROR" "Settings-Dialog Re-Open fehlgeschlagen")
          (setq *SBZ:dlg-running* nil)
        )
        (progn

      ;; === GRUPPE: Dropdown befuellen ===
      (setq group-names (SBZ:get-group-names))
      (start_list "group")
      (add_list "(keine Gruppe)")
      (if group-names
        (foreach gn group-names (add_list gn))
      )
      (end_list)
      (set_tile "group" "0")  ;; Default: keine Gruppe
      (set_tile "groupinfo" "")
      (mode_tile "grp_add" 1)     ;; deaktiviert bis Gruppe gewaehlt
      (mode_tile "grp_remove" 1)  ;; deaktiviert bis Gruppe gewaehlt

      ;; === BOX 1: Zeichnung ===
      (set_tile "bau0" (rtos bau0 2 3))
      ;; Gruppen-Bau0 erstmal leer + disabled
      (set_tile "groupbau0" "")
      (set_tile "usegroupbau0" "0")
      (mode_tile "groupbau0" 1)

      ;; === BOX 2: Modus ===
      (set_tile "copymode" (itoa *SBZ:cfg-copymode*))

      ;; === BOX 3: Block ===
      ;; Block-Farbe Popup
      (start_list "colorblock")
      (foreach c block-colors (add_list (car c)))
      (end_list)
      (set_tile "colorblock" (itoa (SBZ:color-to-index *SBZ:cfg-color-block* block-colors)))
      (set_tile "copyblock" *SBZ:cfg-copyblock*)
      (set_tile "copylayer" *SBZ:cfg-copylayer*)
      (setq scale (SBZ:get-scale))
      (setq suffix (SBZ:get-suffix))
      (set_tile "scale" (rtos scale 2 4))
      (set_tile "suffix" suffix)

      ;; === BOX 4: Attribut ===
      ;; Schriftart
      (start_list "font")
      (foreach fn font-names (add_list fn))
      (end_list)
      (setq font-idx (vl-position (strcase (SBZ:get-font)) (mapcar 'strcase font-names)))
      (if font-idx
        (set_tile "font" (itoa font-idx))
        (set_tile "font" "0")
      )
      ;; Freeze Toggles
      (set_tile "freezeabs" (itoa *SBZ:cfg-freeze-abs*))
      (set_tile "freezerel" (itoa *SBZ:cfg-freeze-rel*))
      (set_tile "freezebau0" (itoa *SBZ:cfg-freeze-bau0*))
      ;; Attribut-Farben
      (start_list "colorabs")
      (foreach c attr-colors (add_list (car c)))
      (end_list)
      (set_tile "colorabs" (itoa (SBZ:color-to-index *SBZ:cfg-color-abs* attr-colors)))
      (start_list "colorrel")
      (foreach c attr-colors (add_list (car c)))
      (end_list)
      (set_tile "colorrel" (itoa (SBZ:color-to-index *SBZ:cfg-color-rel* attr-colors)))
      (start_list "colorbau0")
      (foreach c attr-colors (add_list (car c)))
      (end_list)
      (set_tile "colorbau0" (itoa (SBZ:color-to-index *SBZ:cfg-color-bau0* attr-colors)))
      ;; Dummy popup_lists (Platzhalter in Suffix-Spalte) initialisieren + deaktivieren
      (start_list "dummy1") (add_list "") (end_list) (mode_tile "dummy1" 1)
      (start_list "dummy2") (add_list "") (end_list) (mode_tile "dummy2" 1)
      ;; Kopie-Block Felder deaktivieren wenn Modus aus
      (SBZ:settings-update-copyblock-state (itoa *SBZ:cfg-copymode*))

      ;; --- Action Tiles ---
      (action_tile "copymode" "(SBZ:settings-update-copyblock-state $value)")

      ;; Gruppen-Auswahl: Settings laden wenn Gruppe gewaehlt wird
      (action_tile "group"
        (strcat
          "(if (> (atoi $value) 0)"
          "  (SBZ:load-group-to-dialog (nth (1- (atoi $value)) group-names))"
          ")"
        )
      )

      ;; Gruppen-Bau0 Toggle: Feld aktivieren/deaktivieren
      (action_tile "usegroupbau0"
        "(mode_tile \"groupbau0\" (if (= $value \"1\") 0 1))")

      ;; Gruppe loeschen
      (action_tile "groupdel"
        (strcat
          "(progn"
          "  (setq dlg-group (get_tile \"group\"))"
          "  (if (> (atoi dlg-group) 0)"
          "    (progn"
          "      (setq sel-group (nth (1- (atoi dlg-group)) group-names))"
          "      (SBZ:delete-group sel-group)"
          "      (setq group-names (SBZ:get-group-names))"
          "      (start_list \"group\")"
          "      (add_list \"(keine Gruppe)\")"
          "      (if group-names (foreach gn group-names (add_list gn)))"
          "      (end_list)"
          "      (set_tile \"group\" \"0\")"
          "      (SBZ:update-groupinfo nil)"
          "    )"
          "  )"
          ")"
        )
      )

      ;; Bloecke hinzufuegen
      (action_tile "grp_add" "(SBZ:dlg-grp-add)")

      ;; Bloecke entfernen
      (action_tile "grp_remove" "(SBZ:dlg-grp-remove)")

      ;; Import: Dialog schliessen, Import ausfuehren, Dialog wieder oeffnen
      (action_tile "import" "(done_dialog 12)")

      ;; Standard: Setzt alle Felder auf Werkseinstellungen
      (action_tile "defaults" "(SBZ:reset-defaults)")


      ;; Alle get_tile Strings fuer save/update/recalc (Sub-Dialog-Bug!)
      ;; Gemeinsamer Block: alle Werte in globale Variablen lesen
      (setq *SBZ:dlg-get-all*
        (strcat
          "(setq dlg-bau0 (get_tile \"bau0\"))"
          "(setq dlg-group (get_tile \"group\"))"
          "(setq dlg-groupbau0 (get_tile \"groupbau0\"))"
          "(setq dlg-usegroupbau0 (get_tile \"usegroupbau0\"))"
          
          "(setq dlg-copymode (get_tile \"copymode\"))"
          "(setq dlg-copyblock (get_tile \"copyblock\"))"
          "(setq dlg-copylayer (get_tile \"copylayer\"))"
          "(setq dlg-scale (get_tile \"scale\"))"
          "(setq dlg-suffix (get_tile \"suffix\"))"
          "(setq dlg-colorblock (get_tile \"colorblock\"))"
          "(setq dlg-font (get_tile \"font\"))"
          "(setq dlg-colorabs (get_tile \"colorabs\"))"
          "(setq dlg-colorrel (get_tile \"colorrel\"))"
          "(setq dlg-colorbau0 (get_tile \"colorbau0\"))"
          "(setq dlg-freezeabs (get_tile \"freezeabs\"))"
          "(setq dlg-freezerel (get_tile \"freezerel\"))"
          "(setq dlg-freezebau0 (get_tile \"freezebau0\"))"
        )
      )

      ;; Speichern
      (action_tile "save"
        (strcat *SBZ:dlg-get-all*
          "(setq dlg-action \"save\")(done_dialog 1)"))

      ;; Aendern (= Speichern + bestehende Bloecke loeschen + neu erstellen)
      (action_tile "update"
        (strcat *SBZ:dlg-get-all*
          "(setq dlg-action \"update\")(done_dialog 3)"))

      ;; Schliessen
      (action_tile "close" "(setq dlg-action \"close\")(done_dialog 0)")

      ;; Wenn sel-group bekannt (Re-Open nach Add/Remove), Dropdown setzen
      (if (and sel-group (/= sel-group "") group-names)
        (progn
          (setq *SBZ:dlg-grp-idx*
            (vl-position sel-group group-names))
          (if *SBZ:dlg-grp-idx*
            (progn
              (set_tile "group" (itoa (1+ *SBZ:dlg-grp-idx*)))
              (SBZ:load-group-to-dialog sel-group)
            )
          )
        )
      )

      ;; --- Dialog starten ---
      (setq result (start_dialog))

      ;; === HINZUFUEGEN (result=10) ===
      (cond
        ((= result 10)
          ;; Gruppen-Settings laden
          (if (and sel-group (/= sel-group ""))
            (progn
              (setq sel-group-data (SBZ:load-group sel-group))
              (if sel-group-data
                (progn
                  (setq last-blk (cdr (assoc "QUELLBLOCK" sel-group-data)))
                  (setq last-attr (cdr (assoc "ATTRTAG" sel-group-data)))
                  (princ (strcat "\nBloecke waehlen ('" last-blk "') um zur Gruppe '"
                                 sel-group "' hinzuzufuegen:"))
                  ;; User waehlt interaktiv Quell-Bloecke
                  (setq ss-add (ssget))
                  (if ss-add
                    (progn
                      ;; Post-Filter: nur passende Bloecke behalten
                      (setq ss-filtered (ssadd))
                      (setq i (sslength ss-add))
                      (while (> (setq i (1- i)) -1)
                        (setq ent (ssname ss-add i))
                        (setq ent-data (entget ent))
                        (if (and (= (cdr (assoc 0 ent-data)) "INSERT")
                                 (= (strcase (cdr (assoc 2 ent-data))) (strcase last-blk))
                                 (= (cdr (assoc 410 ent-data)) "Model"))
                          (ssadd ent ss-filtered)
                        )
                      )
                      (if (> (sslength ss-filtered) 0)
                        (progn
                          ;; Gruppen-Settings temporaer laden
                          (SBZ:apply-group-settings sel-group)
                          ;; Bau-0 ermitteln
                          (setq bau0-str (cdr (assoc "BAU0" sel-group-data)))
                          (if (and bau0-str (/= bau0-str ""))
                            (setq bau0 (atof bau0-str))
                            (setq bau0 (SBZ:get-bau0))
                          )
                          ;; Bloecke verarbeiten
                          (setq add-count
                            (SBZ:process-blocks last-blk last-attr bau0
                              (cdr (assoc "ZMODE" sel-group-data))
                              sel-group ss-filtered))
                          (princ (strcat "\n" (itoa add-count) " Bloecke zu Gruppe '"
                                         sel-group "' hinzugefuegt."))
                          (SBZ:log-write "INFO"
                            (strcat "Hinzufuegen: " (itoa add-count) " Bloecke zu '" sel-group "'"))
                        )
                        (princ "\nKeine passenden Bloecke in der Auswahl.")
                      )
                    )
                    (princ "\nKeine Auswahl.")
                  )
                )
              )
            )
          )
        ) ;; end result=10

        ;; === ENTFERNEN (result=11) ===
        ((= result 11)
          (if (and sel-group (/= sel-group ""))
            (progn
              (setq copy-blk-name (SBZ:build-copyblock-name sel-group))
              (princ (strcat "\nKopie-Bloecke waehlen ('" copy-blk-name "') zum Entfernen:"))
              ;; User waehlt interaktiv Kopie-Bloecke
              (setq ss-remove (ssget))
              (if ss-remove
                (progn
                  (setq rem-count 0)
                  (setq i (sslength ss-remove))
                  (while (> (setq i (1- i)) -1)
                    (setq ent (ssname ss-remove i))
                    (setq ent-data (entget ent))
                    ;; Nur Kopie-Bloecke dieser Gruppe entfernen
                    (if (and (= (cdr (assoc 0 ent-data)) "INSERT")
                             (= (strcase (cdr (assoc 2 ent-data))) (strcase copy-blk-name))
                             (= (SBZ:get-xdata ent) sel-group))
                      (progn
                        (entdel ent)
                        (setq rem-count (1+ rem-count))
                      )
                    )
                  )
                  (princ (strcat "\n" (itoa rem-count) " Bloecke aus Gruppe '"
                                 sel-group "' entfernt."))
                  (SBZ:log-write "INFO"
                    (strcat "Entfernen: " (itoa rem-count) " Bloecke aus '" sel-group "'"))
                )
                (princ "\nKeine Auswahl.")
              )
            )
          )
        ) ;; end result=11

        ;; === IMPORT (result=12) ===
        ((= result 12)
          (SBZ:log-write "INFO" "Settings: Import gestartet")
          (SBZ:run-import-dialog)
          ;; Gruppen-Liste aktualisieren nach Import
          (setq group-names (SBZ:get-group-names))
        ) ;; end result=12

        ;; === NORMAL: Save/Update/Close (result=0,1,3) → Schleife beenden ===
        (T (setq *SBZ:dlg-running* nil))
      ) ;; end cond

      )) ;; end progn + if new_dialog
      ) ;; end while

      ;; --- Dialog geschlossen, Werte auswerten ---
      (if (and dlg-action (/= dlg-action "close"))
        (progn
          ;; Gewaehlte Gruppe ermitteln
          (setq sel-group
            (if (and dlg-group (> (atoi dlg-group) 0) group-names)
              (nth (1- (atoi dlg-group)) group-names)
              nil
            )
          )
          ;; DWG Bau-0 aus Dialog lesen
          (setq bau0 (atof (vl-string-subst "." "," dlg-bau0)))

          ;; =============================================================
          ;; SPEICHERN: Globale Settings + Config-Datei + Gruppe (optional)
          ;; =============================================================
          (if (= dlg-action "save")
            (progn
              ;; DWG Bau-0 als Custom Property speichern
              (SBZ:set-bau0 bau0)
              ;; Globale Variablen aus Dialog-Werten setzen
              (setq *SBZ:cfg-copymode* (atoi dlg-copymode))
              (if (and dlg-copyblock (/= dlg-copyblock ""))
                (setq *SBZ:cfg-copyblock* dlg-copyblock))
              (if (and dlg-copylayer (/= dlg-copylayer ""))
                (setq *SBZ:cfg-copylayer* dlg-copylayer))
              (if (and dlg-scale (/= dlg-scale ""))
                (progn
                  (setq scale (atof dlg-scale))
                  (if (> scale 0.0) (SBZ:set-scale scale))))
              (if dlg-suffix (SBZ:set-suffix dlg-suffix))
              (if (and dlg-font font-names)
                (progn
                  (setq *SBZ:cfg-font* (nth (atoi dlg-font) font-names))
                  (SBZ:set-font *SBZ:cfg-font*)))
              (if dlg-colorblock
                (setq *SBZ:cfg-color-block* (cdr (nth (atoi dlg-colorblock) block-colors))))
              (if dlg-colorabs
                (setq *SBZ:cfg-color-abs* (cdr (nth (atoi dlg-colorabs) attr-colors))))
              (if dlg-colorrel
                (setq *SBZ:cfg-color-rel* (cdr (nth (atoi dlg-colorrel) attr-colors))))
              (if dlg-colorbau0
                (setq *SBZ:cfg-color-bau0* (cdr (nth (atoi dlg-colorbau0) attr-colors))))
              (setq *SBZ:cfg-freeze-abs* (atoi dlg-freezeabs))
              (setq *SBZ:cfg-freeze-rel* (atoi dlg-freezerel))
              (setq *SBZ:cfg-freeze-bau0* (atoi dlg-freezebau0))
              ;; Config-Datei schreiben
              (SBZ:save-config)
              (SBZ:log-write "INFO" "Globale Settings + Config gespeichert")
              (princ "\nEinstellungen gespeichert.")
              ;; Wenn Gruppe gewaehlt: Gruppen-XRecord auch aktualisieren
              (if sel-group
                (progn
                  (setq bau0-str
                    (if (= dlg-usegroupbau0 "1") dlg-groupbau0 ""))
                  (setq sel-group-data (SBZ:load-group sel-group))
                  (SBZ:save-group sel-group
                    (SBZ:group-data-from-current
                      (if sel-group-data (cdr (assoc "QUELLBLOCK" sel-group-data)) "")
                      (if sel-group-data (cdr (assoc "ATTRTAG" sel-group-data)) "")
                      bau0-str
                      (if sel-group-data (cdr (assoc "ZMODE" sel-group-data)) "REL")
                      sel-group))
                  (SBZ:log-write "INFO"
                    (strcat "Gruppe '" sel-group "' XRecord aktualisiert"))
                  (princ (strcat "\nGruppe '" sel-group "' aktualisiert."))
                )
              )
            )
          )

          ;; =============================================================
          ;; AENDERN: NUR Gruppe aktualisieren + Bloecke neu erstellen
          ;; Globale Variablen werden NICHT dauerhaft geaendert!
          ;; =============================================================
          (if (= dlg-action "update")
            (if sel-group
              ;; === GRUPPEN-MODUS: Gruppe aendern ===
              (progn
                (setq sel-group-data (SBZ:load-group sel-group))
                (if sel-group-data
                  (progn
                    (setq last-blk (cdr (assoc "QUELLBLOCK" sel-group-data)))
                    (setq last-attr (cdr (assoc "ATTRTAG" sel-group-data)))
                    (setq bau0-str
                      (if (= dlg-usegroupbau0 "1") dlg-groupbau0 ""))
                    (SBZ:log-write "INFO"
                      (strcat "Aendern Gruppe '" sel-group "': Block='"
                              last-blk "' Attr='" last-attr "'"))

                    ;; Globale Variablen SICHERN
                    (setq old-copyblock *SBZ:cfg-copyblock*)
                    (setq *save-copylayer* *SBZ:cfg-copylayer*)
                    (setq *save-font* *SBZ:cfg-font*)
                    (setq *save-color-block* *SBZ:cfg-color-block*)
                    (setq *save-color-abs* *SBZ:cfg-color-abs*)
                    (setq *save-color-rel* *SBZ:cfg-color-rel*)
                    (setq *save-color-bau0* *SBZ:cfg-color-bau0*)
                    (setq *save-freeze-abs* *SBZ:cfg-freeze-abs*)
                    (setq *save-freeze-rel* *SBZ:cfg-freeze-rel*)
                    (setq *save-freeze-bau0* *SBZ:cfg-freeze-bau0*)
                    ;; DWG Custom Properties sichern
                    (setq *save-scale* (SBZ:get-scale))
                    (setq *save-suffix* (SBZ:get-suffix))
                    (setq *save-dwg-font* (SBZ:get-font))

                    ;; Dialog-Werte TEMPORAER in globale Vars laden
                    (if (and dlg-copylayer (/= dlg-copylayer ""))
                      (setq *SBZ:cfg-copylayer* dlg-copylayer))
                    (if (and dlg-font font-names)
                      (progn
                        (setq *SBZ:cfg-font* (nth (atoi dlg-font) font-names))
                        (SBZ:set-font *SBZ:cfg-font*)))
                    (if dlg-colorblock
                      (setq *SBZ:cfg-color-block* (cdr (nth (atoi dlg-colorblock) block-colors))))
                    (if dlg-colorabs
                      (setq *SBZ:cfg-color-abs* (cdr (nth (atoi dlg-colorabs) attr-colors))))
                    (if dlg-colorrel
                      (setq *SBZ:cfg-color-rel* (cdr (nth (atoi dlg-colorrel) attr-colors))))
                    (if dlg-colorbau0
                      (setq *SBZ:cfg-color-bau0* (cdr (nth (atoi dlg-colorbau0) attr-colors))))
                    (setq *SBZ:cfg-freeze-abs* (atoi dlg-freezeabs))
                    (setq *SBZ:cfg-freeze-rel* (atoi dlg-freezerel))
                    (setq *SBZ:cfg-freeze-bau0* (atoi dlg-freezebau0))
                    (if (and dlg-scale (/= dlg-scale ""))
                      (SBZ:set-scale (atof dlg-scale)))
                    (if dlg-suffix (SBZ:set-suffix dlg-suffix))

                    ;; Pruefen ob Import-Gruppe (kein Quell-Block)
                    (if (= last-blk "IMPORT")
                      (progn
                        ;; IMPORT-GRUPPE: Bloecke direkt aktualisieren (nicht loeschen!)
                        (SBZ:log-write "INFO"
                          (strcat "Aendern Import-Gruppe '" sel-group "'"))
                        ;; Gruppen-XRecord aktualisieren
                        (SBZ:save-group sel-group
                          (SBZ:group-data-from-current
                            last-blk last-attr bau0-str
                            (cdr (assoc "ZMODE" sel-group-data))
                            sel-group))
                        ;; Bau-0 fuer Recalc
                        (if (and (= dlg-usegroupbau0 "1")
                                 dlg-groupbau0 (/= dlg-groupbau0 ""))
                          (setq bau0 (atof (vl-string-subst "." "," dlg-groupbau0)))
                        )
                        ;; Visuelle Eigenschaften aktualisieren
                        (setq count (SBZ:update-group-visual sel-group))
                        (princ (strcat "\n" (itoa count) " Bloecke in Gruppe '"
                                       sel-group "' aktualisiert."))
                      )
                      (progn
                        ;; NORMALE GRUPPE: Quell-Bloecke suchen, loeschen, neu erstellen

                    ;; 1. Quell-Bloecke dieser Gruppe finden (via Kopie-Positionen)
                    ;; MUSS VOR delete-group passieren!
                    (setq ss-work
                      (SBZ:get-source-ss-for-group sel-group last-blk))

                    ;; 2. Alte Entities dieser Gruppe loeschen
                    (SBZ:delete-group sel-group)

                    ;; 3. Gruppen-XRecord mit Dialog-Werten speichern
                    (SBZ:save-group sel-group
                      (SBZ:group-data-from-current
                        last-blk last-attr bau0-str
                        (cdr (assoc "ZMODE" sel-group-data))
                        sel-group))

                    ;; 4. Bau-0 fuer process-blocks bestimmen
                    (if (and (= dlg-usegroupbau0 "1")
                             dlg-groupbau0 (/= dlg-groupbau0 ""))
                      (setq bau0 (atof (vl-string-subst "." "," dlg-groupbau0)))
                    )

                    ;; 5. Bloecke neu erstellen (NUR die Quell-Bloecke der Gruppe!)
                    (if ss-work
                      (progn
                        (setq count
                          (SBZ:process-blocks last-blk last-attr bau0
                            (cdr (assoc "ZMODE" sel-group-data)) sel-group ss-work))
                        (princ (strcat "\n" (itoa count) " Bloecke in Gruppe '"
                                       sel-group "' neu erstellt."))
                      )
                      (progn
                        (princ "\nKeine Quell-Bloecke fuer diese Gruppe gefunden.")
                        (SBZ:log-write "WARN"
                          (strcat "Aendern: Keine Quell-Bloecke fuer Gruppe '" sel-group "'"))
                      )
                    )

                    )) ;; end progn + if IMPORT check

                    ;; 6. Globale Variablen WIEDERHERSTELLEN
                    (setq *SBZ:cfg-copyblock* old-copyblock)
                    (setq *SBZ:cfg-copylayer* *save-copylayer*)
                    (setq *SBZ:cfg-font* *save-font*)
                    (setq *SBZ:cfg-color-block* *save-color-block*)
                    (setq *SBZ:cfg-color-abs* *save-color-abs*)
                    (setq *SBZ:cfg-color-rel* *save-color-rel*)
                    (setq *SBZ:cfg-color-bau0* *save-color-bau0*)
                    (setq *SBZ:cfg-freeze-abs* *save-freeze-abs*)
                    (setq *SBZ:cfg-freeze-rel* *save-freeze-rel*)
                    (setq *SBZ:cfg-freeze-bau0* *save-freeze-bau0*)
                    ;; DWG Custom Properties wiederherstellen
                    (SBZ:set-scale *save-scale*)
                    (SBZ:set-suffix *save-suffix*)
                    (SBZ:set-font *save-dwg-font*)
                    (SBZ:log-write "INFO" "Globale Settings + Custom Properties wiederhergestellt")
                  )
                  (progn
                    (princ "\nGruppen-Daten nicht gefunden.")
                    (SBZ:log-write "ERROR"
                      (strcat "Gruppe '" sel-group "' Daten nicht lesbar"))
                  )
                )
              )
              ;; === KEINE GRUPPE GEWAEHLT: Hinweis ===
              (progn
                (princ "\nAendern: Bitte zuerst eine Gruppe waehlen.")
                (SBZ:log-write "WARN" "Aendern ohne Gruppe nicht moeglich")
              )
            )
          )
        )
        ;; Schliessen ohne Speichern
        (progn
          (princ "\nEinstellungen nicht geaendert.")
          (SBZ:log-write "INFO" "Settings: Geschlossen ohne Speichern")
        )
      )

      ;; Cleanup DCL
      (unload_dialog dcl-id)
      (vl-file-delete dcl-file)
    )
  )

  (SBZ:log-write "INFO" "Befehl SBZSETTINGS beendet")
  (princ)
)


;;; ----------------------------------------------------------------------------
;;; c:SBZDEBUG - Debug-Modus Toggle
;;; ----------------------------------------------------------------------------
(defun c:SBZDEBUG ( / )
  (SBZ:ensure-init)
  (setq *SBZ:debug-mode* (not *SBZ:debug-mode*))
  (princ (strcat "\nSBZ Debug-Modus: "
    (if *SBZ:debug-mode* "EIN" "AUS")))
  (SBZ:log-write "INFO"
    (strcat "Debug-Modus: " (if *SBZ:debug-mode* "EIN" "AUS")))
  (princ)
)


;;; ----------------------------------------------------------------------------
;;; c:SBZPURGE - Kopie-Bloecke loeschen + Block-Definition purgen
;;; Loescht alle Instanzen des Kopie-Blocks und entfernt die Definition.
;;; Beim naechsten SETBLOCKZ wird die Definition mit aktuellen Settings
;;; (Schriftart, Farben, Texthoehe) neu erstellt.
;;; ----------------------------------------------------------------------------
(defun c:SBZPURGE ( / *error* old-cmdecho blk-name ss count blocks blk-def)
  (SBZ:ensure-init)
  (defun *error* (msg)
    (if (not (SBZ:cancel-p msg))
      (progn
        (princ (strcat "\nFehler: " msg))
        (SBZ:log-write "ERROR" (strcat "SBZPURGE Error-Handler: " msg))
      )
    )
    (if old-cmdecho (setvar "CMDECHO" old-cmdecho))
    (princ)
  )
  (setq old-cmdecho (getvar "CMDECHO"))
  (setvar "CMDECHO" 0)

  (setq blk-name *SBZ:cfg-copyblock*)
  (SBZ:log-write "INFO" (strcat "SBZPURGE: Starte fuer Block '" blk-name "'"))

  ;; Schritt 1: Alle Instanzen im Modelspace loeschen
  (setq ss (ssget "X" (list (cons 2 blk-name) (cons 410 "Model"))))
  (if (and ss (> (sslength ss) 0))
    (progn
      (setq count (sslength ss))
      (command "._erase" ss "")
      (princ (strcat "\n" (itoa count) " '" blk-name "' Bloecke geloescht."))
      (SBZ:log-write "INFO" (strcat (itoa count) " Instanzen geloescht"))
    )
    (progn
      (princ (strcat "\nKeine '" blk-name "' Bloecke im Modelspace gefunden."))
      (SBZ:log-write "INFO" "Keine Instanzen gefunden")
    )
  )

  ;; Schritt 2: Block-Definition purgen
  (setq blocks (vla-get-blocks (vla-get-activedocument (vlax-get-acad-object))))
  (if (not (vl-catch-all-error-p
        (setq blk-def (vl-catch-all-apply 'vla-item (list blocks blk-name)))))
    (progn
      (if (not (vl-catch-all-error-p
            (vl-catch-all-apply 'vla-delete (list blk-def))))
        (progn
          (princ (strcat "\nBlock-Definition '" blk-name "' geloescht."))
          (SBZ:log-write "INFO" (strcat "Block-Definition '" blk-name "' geloescht"))
        )
        (progn
          (princ (strcat "\nBlock-Definition konnte nicht geloescht werden (noch in Verwendung?)."))
          (princ "\nVersuche: PURGE → Bloecke → " blk-name)
          (SBZ:log-write "WARN" "Block-Definition konnte nicht geloescht werden")
        )
      )
    )
    (progn
      (princ (strcat "\nBlock-Definition '" blk-name "' existiert nicht."))
      (SBZ:log-write "INFO" "Block-Definition existiert nicht")
    )
  )

  (princ "\nBeim naechsten SETBLOCKZ wird der Block mit aktuellen Settings neu erstellt.")
  (if old-cmdecho (setvar "CMDECHO" old-cmdecho))
  (SBZ:log-write "INFO" "SBZPURGE beendet")
  (princ)
)


;;; ============================================================================
;;; INITIALISIERUNG (NUR PRINC!)
;;; ============================================================================

(princ (strcat "\nSetBlockZ.lsp v" *SBZ:version* " geladen."))
(princ "\nBefehle: SETBLOCKZ | SBZSETTINGS | SBZIMPORT | SBZPURGE | SBZDEBUG")
(princ)
